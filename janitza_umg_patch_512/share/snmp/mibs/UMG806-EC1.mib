COMPANY-UNTITLED-MIB DEFINITIONS ::= BEGIN
 
		IMPORTS
			OBJECT-TYPE			
				FROM RFC-1212;
	
	
--
-- Node definitions
--
	
		-- 1
		iso OBJECT IDENTIFIER ::= {  1 }

		
		-- 1.3
		org OBJECT IDENTIFIER ::= { iso 3 }

		
		-- 1.3.2
		sfere OBJECT IDENTIFIER ::= { org 2 }

		
		-- 1.3.2.1
		module OBJECT IDENTIFIER ::= { sfere 1 }

		
		-- 1.3.2.1.1
		ec1 OBJECT IDENTIFIER ::= { module 1 }

		
		-- 1.3.2.1.1.1
		mesurementValues OBJECT IDENTIFIER ::= { ec1 1 }

		
		-- 1.3.2.1.1.1.1
		voltageL1N OBJECT-TYPE
			SYNTAX OCTET STRING
			ACCESS read-only
			STATUS mandatory
			::= { mesurementValues 1 }

		
		-- 1.3.2.1.1.1.2
		voltageL2N OBJECT-TYPE
			SYNTAX OCTET STRING
			ACCESS read-only
			STATUS mandatory
			::= { mesurementValues 2 }

		
		-- 1.3.2.1.1.1.3
		voltageL3N OBJECT-TYPE
			SYNTAX OCTET STRING
			ACCESS read-only
			STATUS mandatory
			::= { mesurementValues 3 }

		
		-- 1.3.2.1.1.1.4
		voltageL1L2 OBJECT-TYPE
			SYNTAX OCTET STRING
			ACCESS read-only
			STATUS mandatory
			::= { mesurementValues 4 }

		
		-- 1.3.2.1.1.1.5
		voltageL2L3 OBJECT-TYPE
			SYNTAX OCTET STRING
			ACCESS read-only
			STATUS mandatory
			::= { mesurementValues 5 }

		
		-- 1.3.2.1.1.1.6
		voltageL3L1 OBJECT-TYPE
			SYNTAX OCTET STRING
			ACCESS read-only
			STATUS mandatory
			::= { mesurementValues 6 }

		
		-- 1.3.2.1.1.1.7
		apparentCurrentL1N OBJECT-TYPE
			SYNTAX OCTET STRING
			ACCESS read-only
			STATUS mandatory
			::= { mesurementValues 7 }

		
		-- 1.3.2.1.1.1.8
		apparentCurrentL2N OBJECT-TYPE
			SYNTAX OCTET STRING
			ACCESS read-only
			STATUS mandatory
			::= { mesurementValues 8 }

		
		-- 1.3.2.1.1.1.9
		apparentCurrentL3N OBJECT-TYPE
			SYNTAX OCTET STRING
			ACCESS read-only
			STATUS mandatory
			::= { mesurementValues 9 }

		
		-- 1.3.2.1.1.1.10
		apparentCurrentL4N OBJECT-TYPE
			SYNTAX OCTET STRING
			ACCESS read-only
			STATUS mandatory
			::= { mesurementValues 10 }

		
		-- 1.3.2.1.1.1.11
		realPowerL1N OBJECT-TYPE
			SYNTAX OCTET STRING
			ACCESS read-only
			STATUS mandatory
			::= { mesurementValues 11 }

		
		-- 1.3.2.1.1.1.12
		realPowerL2N OBJECT-TYPE
			SYNTAX OCTET STRING
			ACCESS read-only
			STATUS mandatory
			::= { mesurementValues 12 }

		
		-- 1.3.2.1.1.1.13
		realPowerL3N OBJECT-TYPE
			SYNTAX OCTET STRING
			ACCESS read-only
			STATUS mandatory
			::= { mesurementValues 13 }

		
		-- 1.3.2.1.1.1.14
		pSum3 OBJECT-TYPE
			SYNTAX OCTET STRING
			ACCESS read-only
			STATUS mandatory
			::= { mesurementValues 14 }

		
		-- 1.3.2.1.1.1.15
		reactivePowerL1 OBJECT-TYPE
			SYNTAX OCTET STRING
			ACCESS read-only
			STATUS mandatory
			::= { mesurementValues 15 }

		
		-- 1.3.2.1.1.1.16
		reactivePowerL2 OBJECT-TYPE
			SYNTAX OCTET STRING
			ACCESS read-only
			STATUS mandatory
			::= { mesurementValues 16 }

		
		-- 1.3.2.1.1.1.17
		reactivePowerL3 OBJECT-TYPE
			SYNTAX OCTET STRING
			ACCESS read-only
			STATUS mandatory
			::= { mesurementValues 17 }

		
		-- 1.3.2.1.1.1.18
		qSum3 OBJECT-TYPE
			SYNTAX OCTET STRING
			ACCESS read-only
			STATUS mandatory
			::= { mesurementValues 18 }

		
		-- 1.3.2.1.1.1.19
		cosPhiUL1IL1 OBJECT-TYPE
			SYNTAX OCTET STRING
			ACCESS read-only
			STATUS mandatory
			::= { mesurementValues 19 }

		
		-- 1.3.2.1.1.1.20
		cosPhiUL1IL2 OBJECT-TYPE
			SYNTAX OCTET STRING
			ACCESS read-only
			STATUS mandatory
			::= { mesurementValues 20 }

		
		-- 1.3.2.1.1.1.21
		cosPhiUL1IL3 OBJECT-TYPE
			SYNTAX OCTET STRING
			ACCESS read-only
			STATUS mandatory
			::= { mesurementValues 21 }

		
		-- 1.3.2.1.1.1.22
		realEnergyL1Consumed OBJECT-TYPE
			SYNTAX OCTET STRING
			ACCESS read-only
			STATUS mandatory
			::= { mesurementValues 22 }

		
		-- 1.3.2.1.1.1.23
		realEnergyL2Consumed OBJECT-TYPE
			SYNTAX OCTET STRING
			ACCESS read-only
			STATUS mandatory
			::= { mesurementValues 23 }

		
		-- 1.3.2.1.1.1.24
		realEnergyL3Consumed OBJECT-TYPE
			SYNTAX OCTET STRING
			ACCESS read-only
			STATUS mandatory
			::= { mesurementValues 24 }

		
		-- 1.3.2.1.1.1.25
		realEnergyL1L2L3Consumed OBJECT-TYPE
			SYNTAX OCTET STRING
			ACCESS read-only
			STATUS mandatory
			::= { mesurementValues 25 }

		
		-- 1.3.2.1.1.1.26
		reactiveEnergyL1 OBJECT-TYPE
			SYNTAX OCTET STRING
			ACCESS read-only
			STATUS mandatory
			::= { mesurementValues 26 }

		
		-- 1.3.2.1.1.1.27
		reactiveEnergyL2 OBJECT-TYPE
			SYNTAX OCTET STRING
			ACCESS read-only
			STATUS mandatory
			::= { mesurementValues 27 }

		
		-- 1.3.2.1.1.1.28
		reactiveEnergyL3 OBJECT-TYPE
			SYNTAX OCTET STRING
			ACCESS read-only
			STATUS mandatory
			::= { mesurementValues 28 }

		
		-- 1.3.2.1.1.1.29
		reactiveEnergyL1L2L3 OBJECT-TYPE
			SYNTAX OCTET STRING
			ACCESS read-only
			STATUS mandatory
			::= { mesurementValues 29 }

		
		-- 1.3.2.1.1.1.30
		harmonicTHDUL1N OBJECT-TYPE
			SYNTAX OCTET STRING
			ACCESS read-only
			STATUS mandatory
			::= { mesurementValues 30 }

		
		-- 1.3.2.1.1.1.31
		harmonicTHDUL2N OBJECT-TYPE
			SYNTAX OCTET STRING
			ACCESS read-only
			STATUS mandatory
			::= { mesurementValues 31 }

		
		-- 1.3.2.1.1.1.32
		harmonicTHDUL3N OBJECT-TYPE
			SYNTAX OCTET STRING
			ACCESS read-only
			STATUS mandatory
			::= { mesurementValues 32 }

		
		-- 1.3.2.1.1.1.33
		harmonicTHDIL1 OBJECT-TYPE
			SYNTAX OCTET STRING
			ACCESS read-only
			STATUS mandatory
			::= { mesurementValues 33 }

		
		-- 1.3.2.1.1.1.34
		harmonicTHDIL2 OBJECT-TYPE
			SYNTAX OCTET STRING
			ACCESS read-only
			STATUS mandatory
			::= { mesurementValues 34 }

		
		-- 1.3.2.1.1.1.35
		harmonicTHDIL3 OBJECT-TYPE
			SYNTAX OCTET STRING
			ACCESS read-only
			STATUS mandatory
			::= { mesurementValues 35 }

		
		-- 1.3.2.1.1.1.36
		umg806I5Inputs OBJECT-TYPE
			SYNTAX OCTET STRING
			ACCESS read-only
			STATUS mandatory
			::= { mesurementValues 36 }

		
		-- 1.3.2.1.1.1.37
		umg806PT100 OBJECT-TYPE
			SYNTAX OCTET STRING
			ACCESS read-only
			STATUS mandatory
			::= { mesurementValues 37 }

		
	
	END
