JANITZA-MIB DEFINITIONS ::= BEGIN
                IMPORTS
                  sysUpTime, DisplayString        
                                FROM RFC1213-MIB
                        OBJECT-TYPE
                                FROM RFC-1212
                        mib-2
                                FROM SNMPv2-SMI
                        enterprises, TimeTicks
                                FROM RFC1155-SMI;




system       OBJECT IDENTIFIER ::= { mib-2 1 }
snmp         OBJECT IDENTIFIER ::= { mib-2 11 }

sysDescr OBJECT-TYPE
    SYNTAX OCTET STRING
    ACCESS  read-only
    STATUS  current
    DESCRIPTION
            "A textual description of the entity.  This value should
            include the full name and version identification of
            the system's hardware type, software operating-system,
            and networking software."
    ::= { system 1 }

sysObjectID OBJECT-TYPE
    SYNTAX      OBJECT IDENTIFIER
    ACCESS  read-only
    STATUS      current
    DESCRIPTION
            "The vendor's authoritative identification of the
            network management subsystem contained in the entity.
            This value is allocated within the SMI enterprises
            subtree (1.3.6.1.4.1) and provides an easy and
            unambiguous means for determining `what kind of box' is
            being managed.  For example, if vendor `Flintstones,
            Inc.' was assigned the subtree 1.3.6.1.4.1.424242,
            it could assign the identifier 1.3.6.1.4.1.424242.1.1
            to its `Fred Router'."
    ::= { system 2 }

sysUpTime OBJECT-TYPE
	SYNTAX      TimeTicks
	ACCESS  read-only
	STATUS      current
	DESCRIPTION
			"The time (in hundredths of a second) since the
			network management portion of the system was last
			re-initialized."
	::= { system 3 }


sysName OBJECT-TYPE
    SYNTAX OCTET STRING
    ACCESS  read-write
    STATUS      current
    DESCRIPTION
            "An administratively-assigned name for this managed
            node.  By convention, this is the node's fully-qualified
            domain name.  If the name is unknown, the value is
            the zero-length string."
    ::= { system 5 }

sysLocation OBJECT-TYPE
        SYNTAX OCTET STRING
    ACCESS  read-write
    STATUS      current
    DESCRIPTION
            "The physical location of this node (e.g., 'telephone
            closet, 3rd floor').  If the location is unknown, the
            value is the zero-length string."
    ::= { system 6 }

sysServices OBJECT-TYPE
    SYNTAX      INTEGER (0..127)
    ACCESS  read-only
    STATUS      current
    DESCRIPTION
            "A value which indicates the set of services that this
            entity may potentially offer.  The value is a sum.

            This sum initially takes the value zero. Then, for
            each layer, L, in the range 1 through 7, that this node
            performs transactions for, 2 raised to (L - 1) is added
            to the sum.  For example, a node which performs only
            routing functions would have a value of 4 (2^(3-1)).
            In contrast, a node which is a host offering application
            services would have a value of 72 (2^(4-1) + 2^(7-1)).
            Note that in the context of the Internet suite of
            protocols, values should be calculated accordingly:

                 layer      functionality
                   1        physical (e.g., repeaters)
                   2        datalink/subnetwork (e.g., bridges)
                   3        internet (e.g., supports the IP)
                   4        end-to-end  (e.g., supports the TCP)
                   7        applications (e.g., supports the SMTP)

            For systems including OSI protocols, layers 5 and 6
            may also be counted."
    ::= { system 7 }



        janitza OBJECT IDENTIFIER ::= { enterprises 34278}

        rmsPhase OBJECT IDENTIFIER ::= { janitza 1 }

        uLN1 OBJECT-TYPE
                SYNTAX INTEGER
                ACCESS read-write
                STATUS mandatory
    DESCRIPTION
                "Voltage Phase L1 in 100mV"
                ::= { rmsPhase 1 }

        uLN2 OBJECT-TYPE
                SYNTAX INTEGER
                ACCESS read-write
                STATUS mandatory
    DESCRIPTION
                "Voltage Phase L2 in 100mV"
                ::= { rmsPhase 2 }

        uLN3 OBJECT-TYPE
                SYNTAX INTEGER
                ACCESS read-write
                STATUS mandatory
    DESCRIPTION
                "Voltage Phase L3 in 100mV"
                ::= { rmsPhase 3 }

        uL1L2 OBJECT-TYPE
                SYNTAX INTEGER
                ACCESS read-write
                STATUS mandatory
    DESCRIPTION
                "Voltage Phase L1-L2 in 100mV"
                ::= { rmsPhase 4 }

        uL2L3 OBJECT-TYPE
                SYNTAX INTEGER
                ACCESS read-write
                STATUS mandatory
    DESCRIPTION
                "Voltage Phase L2-L3 in 100mV"
                ::= {  rmsPhase 5 }

        uL3L1 OBJECT-TYPE
                SYNTAX INTEGER
                ACCESS read-write
                STATUS mandatory
    DESCRIPTION
                "Voltage Phase L3-L1 in 100mV"
                ::= { rmsPhase 6 }

        iL1     OBJECT-TYPE
                SYNTAX INTEGER
                ACCESS read-write
                STATUS mandatory
    DESCRIPTION
                "Current Phase L1  in 1mA"
                ::= { rmsPhase 7 }

        iL2     OBJECT-TYPE
                SYNTAX INTEGER
                ACCESS read-write
                STATUS mandatory
    DESCRIPTION
                "Current Phase L2  in 1mA"
                ::= { rmsPhase 8 }

        iL3     OBJECT-TYPE
                SYNTAX INTEGER
                ACCESS read-write
                STATUS mandatory
    DESCRIPTION
                "Current Phase L3  in 1mA"
                ::= { rmsPhase 9 }
                
        iL4     OBJECT-TYPE
                SYNTAX INTEGER
                ACCESS read-write
                STATUS mandatory
    DESCRIPTION
                "Current Phase L4  in 1mA"
                ::= { rmsPhase 10 }
                
        iL5     OBJECT-TYPE
                SYNTAX INTEGER
                ACCESS read-write
                STATUS mandatory
    DESCRIPTION
                "Current Phase L5  in 1mA"
                ::= { rmsPhase 11 }
                
		iL6     OBJECT-TYPE
                SYNTAX INTEGER
                ACCESS read-write
                STATUS mandatory
    DESCRIPTION
                "Current Phase L6 in 1mA"
                ::= { rmsPhase 12 }
        pL1     OBJECT-TYPE
                SYNTAX INTEGER
                ACCESS read-write
                STATUS mandatory
    DESCRIPTION
                "Real Power L1  in Watt"
                ::= { rmsPhase 13 }

        pL2     OBJECT-TYPE
                SYNTAX INTEGER
                ACCESS read-write
                STATUS mandatory
    DESCRIPTION
                "Real Power L2  in Watt"
                ::= { rmsPhase 14 }

        pL3     OBJECT-TYPE
                SYNTAX INTEGER
                ACCESS read-write
                STATUS mandatory
    DESCRIPTION
                "Real Power L3  in Watt"
                ::= { rmsPhase 15 }

        qL1     OBJECT-TYPE
                SYNTAX INTEGER
                ACCESS read-write
                STATUS mandatory
    DESCRIPTION
                "Reaktiv Power L1  in VAr"
                ::= { rmsPhase 16 }

        qL2     OBJECT-TYPE
                SYNTAX INTEGER
                ACCESS read-write
                STATUS mandatory
    DESCRIPTION
                "Reaktiv Power L2  in VAr"
                ::= { rmsPhase 17 }

        qL3     OBJECT-TYPE
                SYNTAX INTEGER
                ACCESS read-write
                STATUS mandatory
    DESCRIPTION
                "Reaktiv Power L3  in VAr"
                ::= { rmsPhase 18 }

        sL1     OBJECT-TYPE
                SYNTAX INTEGER
                ACCESS read-write
                STATUS mandatory
    DESCRIPTION
                "Power L1  in VA"
                ::= { rmsPhase 19 }

        sL2     OBJECT-TYPE
                SYNTAX INTEGER
                ACCESS read-write
                STATUS mandatory
    DESCRIPTION
                "Power L2  in VA"
                ::= { rmsPhase 20 }

        sL3     OBJECT-TYPE
                SYNTAX INTEGER
                ACCESS read-write
                STATUS mandatory
    DESCRIPTION
                "Power L3  in VA"
                ::= { rmsPhase 21 }

        cosPL1  OBJECT-TYPE
                SYNTAX INTEGER
                ACCESS read-write
                STATUS mandatory
    DESCRIPTION
                "Cos(Phi) L1 * 0.001"
                ::= { rmsPhase 22 }

        cosPL2  OBJECT-TYPE
                SYNTAX INTEGER
                ACCESS read-write
                STATUS mandatory
    DESCRIPTION
                "Cos(Phi) L2 * 0.001"
                ::= { rmsPhase 23 }

        cosPL3  OBJECT-TYPE
                SYNTAX INTEGER
                ACCESS read-write
                STATUS mandatory
    DESCRIPTION
                "Cos(Phi) L3 * 0.001"
                ::= { rmsPhase 24 }


        rmsSum OBJECT IDENTIFIER ::= { janitza 2 }

        p3     OBJECT-TYPE
                SYNTAX INTEGER
                ACCESS read-write
                STATUS mandatory
    DESCRIPTION
                "Real Power Sum L1..L3  in Watt"
                ::= { rmsSum 1}

        q3      OBJECT-TYPE
                SYNTAX INTEGER
                ACCESS read-write
                STATUS mandatory
    DESCRIPTION
                "Reaktiv Power Sum L1..L3  in Watt"
                ::= { rmsSum 2}

        s3      OBJECT-TYPE
                SYNTAX INTEGER
                ACCESS read-write
                STATUS mandatory
    DESCRIPTION
                "Power Sum L1..L3  in Watt"
                ::= { rmsSum 3}

        cosP3   OBJECT-TYPE
                SYNTAX INTEGER
                ACCESS read-write
                STATUS mandatory
    DESCRIPTION
                "COS(Phi) Sum L1..L3  *0.001"
                ::= { rmsSum 4}


        energyPhase OBJECT IDENTIFIER ::= { janitza 3 }

        whL1     OBJECT-TYPE
                SYNTAX INTEGER
                ACCESS read-write
                STATUS mandatory
    DESCRIPTION
                "Active Energy  Phase L1 in 0.1 KWh"
                ::= { energyPhase  1}

        whL2     OBJECT-TYPE
                SYNTAX INTEGER
                ACCESS read-write
                STATUS mandatory
    DESCRIPTION
                "Active Energy  Phase L2 in 0.1 KWh"
                ::= { energyPhase  2}

        whL3     OBJECT-TYPE
                SYNTAX INTEGER
                ACCESS read-write
                STATUS mandatory
    DESCRIPTION
                "Active Energy  Phase L3 in 0.1 KWh"
                ::= { energyPhase  3}

        qhL1     OBJECT-TYPE
                SYNTAX INTEGER
                ACCESS read-write
                STATUS mandatory
    DESCRIPTION
                "Reactive Energy  Phase L1 in 0.1 KVArh"
                ::= { energyPhase  4}

        qhL2     OBJECT-TYPE
                SYNTAX INTEGER
                ACCESS read-write
                STATUS mandatory
    DESCRIPTION
                "Reactive Energy  Phase L2 in 0.1 KVArh"
                ::= { energyPhase  5}

        qhL3     OBJECT-TYPE
                SYNTAX INTEGER
                ACCESS read-write
                STATUS mandatory
    DESCRIPTION
                "Reactive Energy  Phase L3 in 0.1 KVArh"
                ::= { energyPhase  6}


        energySum OBJECT IDENTIFIER ::= { janitza 4 }

        wh3    OBJECT-TYPE
                SYNTAX INTEGER
                ACCESS read-write
                STATUS mandatory
    DESCRIPTION
                "Active Energy  Sum L1..L3 in 0.1 KWh"
                ::= { energySum 1}

        qh3    OBJECT-TYPE
                SYNTAX INTEGER
                ACCESS read-write
                STATUS mandatory
    DESCRIPTION
                "Reactive Energy  Sum L1..L3 in 0.1 KWh"
                ::= { energySum  2}

        thd OBJECT IDENTIFIER ::= { janitza 5 }

        thdULN1 OBJECT-TYPE
                SYNTAX INTEGER
                ACCESS read-write
                STATUS mandatory
    DESCRIPTION
                "Total Harmonic Distortion Voltage Phase L1 * 0.1%"
                ::= { thd 1 }

        thdULN2 OBJECT-TYPE
                SYNTAX INTEGER
                ACCESS read-write
                STATUS mandatory
    DESCRIPTION
                "Total Harmonic Distortion Voltage Phase L2 * 0.1%"
                ::= { thd 2 }

        thdULN3 OBJECT-TYPE
                SYNTAX INTEGER
                ACCESS read-write
                STATUS mandatory
    DESCRIPTION
                "Total Harmonic Distortion Voltage Phase L3 * 0.1%"
                ::= { thd 3 }

        thdIL1  OBJECT-TYPE
                SYNTAX INTEGER
                ACCESS read-write
                STATUS mandatory
    DESCRIPTION
                "Total Harmonic Distortion Current Phase L1 * 0.1%"
                ::= { thd 4 }

        thdIL2  OBJECT-TYPE
                SYNTAX INTEGER
                ACCESS read-write
                STATUS mandatory
    DESCRIPTION
                "Total Harmonic Distortion Current Phase L2 * 0.1%"
                ::= { thd 5 }

        thdIL3  OBJECT-TYPE
                SYNTAX INTEGER
                ACCESS read-write
                STATUS mandatory
    DESCRIPTION
                "Total Harmonic Distortion Current Phase L3 * 0.1%"
                ::= { thd 6 }

        misc OBJECT IDENTIFIER ::= { janitza 6 }

        frequence        OBJECT-TYPE
                SYNTAX INTEGER
                ACCESS read-write
                STATUS mandatory
    DESCRIPTION
                "Frequence* 0.01 Hz"
                ::= { misc 1 }
                
        temp1   OBJECT-TYPE
                SYNTAX INTEGER
                ACCESS read-write
                STATUS mandatory
    DESCRIPTION
                "Temperatur1 in °C * 10"
                ::= { misc 2 }

        temp2   OBJECT-TYPE
                SYNTAX INTEGER
                ACCESS read-write
                STATUS mandatory
    DESCRIPTION
                "Temperatur2 in °C * 10"
                ::= { misc 3 }
                
        user OBJECT IDENTIFIER ::= { janitza 7 }

        jasicVAR1       OBJECT-TYPE
                SYNTAX INTEGER
                ACCESS read-write
                STATUS mandatory
    DESCRIPTION
                "Jasic User Variable  to user for Jasic :_snmp_uservar[0]"
                ::= { user 1 }

        jasicVAR2       OBJECT-TYPE
                SYNTAX INTEGER
                ACCESS read-write
                STATUS mandatory
    DESCRIPTION
                "Jasic User Variable  to user for Jasic :_snmp_uservar[1]"
                ::= { user 2 }

        jasicVAR3       OBJECT-TYPE
                SYNTAX INTEGER
                ACCESS read-write
                STATUS mandatory
    DESCRIPTION
                "Jasic User Variable  to user for Jasic :_snmp_uservar[2]"
                ::= { user 3 }

        jasicVAR4       OBJECT-TYPE
                SYNTAX INTEGER
                ACCESS read-write
                STATUS mandatory
    DESCRIPTION
                "Jasic User Variable  to user for Jasic :_snmp_uservar[3]"
                ::= { user 4 }

        jasicVAR5       OBJECT-TYPE
                SYNTAX INTEGER
                ACCESS read-write
                STATUS mandatory
    DESCRIPTION
                "Jasic User Variable  to user for Jasic :_snmp_uservar[4]"
                ::= { user 5 }

        jasicVAR6       OBJECT-TYPE
                SYNTAX INTEGER
                ACCESS read-write
                STATUS mandatory
    DESCRIPTION
                "Jasic User Variable  to user for Jasic :_snmp_uservar[5]"
                ::= { user 6 }

        jasicVAR7       OBJECT-TYPE
                SYNTAX INTEGER
                ACCESS read-write
                STATUS mandatory
    DESCRIPTION
                "Jasic User Variable  to user for Jasic :_snmp_uservar[6]"
                ::= { user 7 }

        jasicVAR8       OBJECT-TYPE
                SYNTAX INTEGER
                ACCESS read-write
                STATUS mandatory
    DESCRIPTION
                "Jasic User Variable  to user for Jasic :_snmp_uservar[7]"
                ::= { user 8 }

        jasicVAR9       OBJECT-TYPE
                SYNTAX INTEGER
                ACCESS read-write
                STATUS mandatory
    DESCRIPTION
                "Jasic User Variable  to user for Jasic :_snmp_uservar[8]"
                ::= { user 9 }

        jasicVAR10      OBJECT-TYPE
                SYNTAX INTEGER
                ACCESS read-write
                STATUS mandatory
    DESCRIPTION
                "Jasic User Variable  to user for Jasic :_snmp_uservar[9]"
                ::= { user 10 }

        jasicVAR11      OBJECT-TYPE
                SYNTAX INTEGER
                ACCESS read-write
                STATUS mandatory
    DESCRIPTION
                "Jasic User Variable  to user for Jasic :_snmp_uservar[10]"
                ::= { user 11 }

        jasicVAR12      OBJECT-TYPE
                SYNTAX INTEGER
                ACCESS read-write
                STATUS mandatory
    DESCRIPTION
                "Jasic User Variable  to user for Jasic :_snmp_uservar[11]"
                ::= { user 12 }

        jasicVAR13      OBJECT-TYPE
                SYNTAX INTEGER
                ACCESS read-write
                STATUS mandatory
    DESCRIPTION
                "Jasic User Variable  to user for Jasic :_snmp_uservar[12]"
                ::= { user 13 }

        jasicVAR14      OBJECT-TYPE
                SYNTAX INTEGER
                ACCESS read-write
                STATUS mandatory
    DESCRIPTION
                "Jasic User Variable  to user for Jasic :_snmp_uservar[13]"
                ::= { user 14 }

        jasicVAR15      OBJECT-TYPE
                SYNTAX INTEGER
                ACCESS read-write
                STATUS mandatory
    DESCRIPTION
                "Jasic User Variable  to user for Jasic :_snmp_uservar[14]"
                ::= { user 15 }

        jasicVAR16      OBJECT-TYPE
                SYNTAX INTEGER
                ACCESS read-write
                STATUS mandatory
    DESCRIPTION
                "Jasic User Variable  to user for Jasic :_snmp_uservar[15]"
                ::= { user 16 }



         coldStart TRAP-TYPE
              ENTERPRISE  snmp
              DESCRIPTION
                          "A coldStart trap signifies that the sending
                          protocol entity is reinitializing itself such
                          that the agent's configuration or the rotocol
                          entity implementation may be altered."
              ::= 0

          warmStart TRAP-TYPE
              ENTERPRISE  snmp
              DESCRIPTION
                          "A warmStart trap signifies that the sending
                          protocol entity is reinitializing itself such
                          that neither the agent configuration nor the
                          protocol entity implementation is altered."
              ::= 1



        userTrap1 TRAP-TYPE
                ENTERPRISE janitza 
    DESCRIPTION
                "Jasic Trap  : use type=6 , subtype = 6"
                ::=  6

        userTrap2 TRAP-TYPE
                ENTERPRISE janitza 
    DESCRIPTION
                "Jasic Trap  : use type=6 , subtype = 7"
                ::=  7

        userTrap3 TRAP-TYPE
                ENTERPRISE janitza 
    DESCRIPTION
                "Jasic Trap  : use type=6 , subtype = 8"
                ::=  8

        userTrap4 TRAP-TYPE
                ENTERPRISE janitza 
    DESCRIPTION
                "Jasic Trap  : use type=6 , subtype = 9"
                ::=  9

        userTrap5 TRAP-TYPE
                ENTERPRISE janitza 
    DESCRIPTION
                "Jasic Trap  : use type=6 , subtype = 10"
                ::=  10

        userTrap6 TRAP-TYPE
                ENTERPRISE janitza 
    DESCRIPTION
                "Jasic Trap  : use type=6 , subtype = 11"
                ::=  11

        userTrap7 TRAP-TYPE
                ENTERPRISE janitza 
    DESCRIPTION
                "Jasic Trap  : use type=6 , subtype = 12"
                ::=  12

        userTrap8 TRAP-TYPE
                ENTERPRISE janitza 
    DESCRIPTION
                "Jasic Trap  : use type=6 , subtype = 13"
                ::=  13

        userTrap9 TRAP-TYPE
                ENTERPRISE janitza 
    DESCRIPTION
                "Jasic Trap  : use type=6 , subtype = 14"
                ::=  14

        userTrap10 TRAP-TYPE
                ENTERPRISE janitza 
    DESCRIPTION
                "Jasic Trap  : use type=6 , subtype = 15"
                ::=  15

        userTrap11 TRAP-TYPE
                ENTERPRISE janitza 
    DESCRIPTION
                "Jasic Trap  : use type=6 , subtype = 16"
                ::=  16

        userTrap12 TRAP-TYPE
                ENTERPRISE janitza 
    DESCRIPTION
                "Jasic Trap  : use type=6 , subtype = 17"
                ::=  17

        userTrap13 TRAP-TYPE
                ENTERPRISE janitza 
    DESCRIPTION
                "Jasic Trap  : use type=6 , subtype = 18"
                ::=  18

        userTrap14 TRAP-TYPE
                ENTERPRISE janitza 
    DESCRIPTION
                "Jasic Trap  : use type=6 , subtype = 19"
                ::=  19

        userTrap15 TRAP-TYPE
                ENTERPRISE janitza 
    DESCRIPTION
                "Jasic Trap  : use type=6 , subtype = 20"
                ::=  20

        userTrap16 TRAP-TYPE
                ENTERPRISE janitza 
    DESCRIPTION
                "Jasic Trap  : use type=6 , subtype = 21"
                ::=  21

        END
