-- Software 0104.13.003
--
-- Changes:
--
-- 2011-02-11 EE/Le 
--   Descriptions reviewed.
--
-- 2011-01-11 EE/Le 
--   Trap definitions redefined.
--
-- 2010-12-20 EE/Le 
--   Object pswUnitMainAlarm was formerly misdeclared as pswAirFlowInit
--
-- Copyright (c) 2010, 2011
--
-- WAGNER Group GmbH
-- Schleswigstr. 1-5
-- 30853 Langenhagen
-- Germany
--

RACKSENS2-PSW-MIB DEFINITIONS ::= BEGIN

    IMPORTS 
        enterprises     FROM RFC1155-SMI
        OBJECT-TYPE     FROM RFC-1212
        DisplayString   FROM RFC1213-MIB
        TRAP-TYPE       FROM RFC-1215
        Gauge           FROM RFC1155-SMI
        Opaque          FROM RFC1155-SMI
        TimeTicks       FROM RFC1155-SMI;

    wagner          OBJECT IDENTIFIER ::= { enterprises     34187 }
    racksens2-psw   OBJECT IDENTIFIER ::= { wagner          57948 }
    racksenstrap    OBJECT IDENTIFIER ::= { racksens2-psw   3     }

    ----------------------------------------------------
    -- Traps
    ----------------------------------------------------

    pswExtinguishing-trap   TRAP-TYPE
        ENTERPRISE racksenstrap
        VARIABLES { pswExtinguishing }
        DESCRIPTION
            "Unit extinguishing state changed."
        ::= 1000

    pswCutOffActive-trap   TRAP-TYPE
        ENTERPRISE racksenstrap
        VARIABLES { pswCutOffActive }
        DESCRIPTION
            "Cut-off relay state changed."
        ::= 1001

    pswManualActivation-trap   TRAP-TYPE
        ENTERPRISE racksenstrap
        VARIABLES { pswManualActivation }
        DESCRIPTION
            "Manual activation state changed."
        ::= 1002

    pswMainAlarmD1-trap   TRAP-TYPE
        ENTERPRISE racksenstrap
        VARIABLES { pswMainAlarmD1 }
        DESCRIPTION
            "Detector 1 fire alarm state state changed."
        ::= 1003

    pswMainAlarmD2-trap   TRAP-TYPE
        ENTERPRISE racksenstrap
        VARIABLES { pswMainAlarmD2 }
        DESCRIPTION
            "Detector 2 fire alarm state state changed."
        ::= 1004

    pswPreAlarmD1-trap   TRAP-TYPE
        ENTERPRISE racksenstrap
        VARIABLES { pswPreAlarmD1 }
        DESCRIPTION
            "Detector 1 action alarm state state changed."
        ::= 1005

    pswPreAlarmD2-trap   TRAP-TYPE
        ENTERPRISE racksenstrap
        VARIABLES { pswPreAlarmD2 }
        DESCRIPTION
            "Detector 2 action alarm state state changed."
        ::= 1006

    pswTemperatureAlarm1-trap   TRAP-TYPE
        ENTERPRISE racksenstrap
        VARIABLES { pswTemperatureAlarm1 }
        DESCRIPTION
            "Temperature sensor 1 alarm state state changed."
        ::= 1007

    pswTemperatureAlarm2-trap   TRAP-TYPE
        ENTERPRISE racksenstrap
        VARIABLES { pswTemperatureAlarm2 }
        DESCRIPTION
            "Temperature sensor 2 alarm state state changed."
        ::= 1008

    pswTemperatureAlarm3-trap   TRAP-TYPE
        ENTERPRISE racksenstrap
        VARIABLES { pswTemperatureAlarm3 }
        DESCRIPTION
            "Temperature sensor 3 alarm state state changed."
        ::= 1009

    pswTemperatureAlarm4-trap   TRAP-TYPE
        ENTERPRISE racksenstrap
        VARIABLES { pswTemperatureAlarm4 }
        DESCRIPTION
            "Temperature sensor 4 alarm state state changed."
        ::= 1010

    pswTemperatureAlarm5-trap   TRAP-TYPE
        ENTERPRISE racksenstrap
        VARIABLES { pswTemperatureAlarm5 }
        DESCRIPTION
            "Temperature sensor 5 alarm state state changed."
        ::= 1011

    pswFailure-trap   TRAP-TYPE
        ENTERPRISE racksenstrap
        VARIABLES { pswFailure }
        DESCRIPTION
            "Failure state changed."
        ::= 1012

    pswServiceOrBlocked-trap   TRAP-TYPE
        ENTERPRISE racksenstrap
        VARIABLES { pswServiceOrBlocked }
        DESCRIPTION
            "Blocked state changed."
        ::= 1013

    pswDoorState-trap   TRAP-TYPE
        ENTERPRISE racksenstrap
        VARIABLES { pswDoorState }
        DESCRIPTION
            "Door open state changed."
        ::= 1014

    pswUnitMainAlarm-trap   TRAP-TYPE
        ENTERPRISE racksenstrap
        VARIABLES { pswUnitMainAlarm }
        DESCRIPTION
            "Unit fire alarm state changed."
        ::= 1015

    ----------------------------------------------------
    ----------------------------------------------------

    basicTable OBJECT-TYPE
        SYNTAX SEQUENCE OF BasicEntry
        ACCESS not-accessible
        STATUS mandatory
        ::= { racksens2-psw 1 }

    basicEntry OBJECT-TYPE
        SYNTAX BasicEntry
        ACCESS not-accessible
        STATUS mandatory
        DESCRIPTION
            "This is the table for basic entries!"
        INDEX { basicIndex }
        ::= { basicTable 1 }

    BasicEntry ::= SEQUENCE {
        basicIndex                  INTEGER,
        rsManufacturer              DisplayString,
        rsUnitName                  DisplayString,
        rsUnitVersion               DisplayString,
        rsObjectTableLoadingState   INTEGER,
        rsObjectTableEntries        INTEGER,
        rsObjectDataValid           INTEGER,
        rsProcessData               OCTET STRING,
        
        -- Process data bits
        
        pswExtinguishing            INTEGER,
        pswCutOffActive             INTEGER,
        pswManualActivation         INTEGER,
        pswMainAlarmD1              INTEGER,
        pswMainAlarmD2              INTEGER,
        pswPreAlarmD1               INTEGER,
        pswPreAlarmD2               INTEGER,
        pswTemperatureAlarm1        INTEGER,
        pswTemperatureAlarm2        INTEGER,
        pswTemperatureAlarm3        INTEGER,
        pswTemperatureAlarm4        INTEGER,
        pswTemperatureAlarm5        INTEGER,
        pswFailure                  INTEGER,
        pswServiceOrBlocked         INTEGER,
        pswDoorState                INTEGER,
        pswUnitMainAlarm            INTEGER
    }

    ----------------------------------------------------
    -- RackSens basic data
    ----------------------------------------------------

    basicIndex OBJECT-TYPE
        SYNTAX  INTEGER (0..1)
        ACCESS  read-only
        STATUS  mandatory
        DESCRIPTION
                "A unique value for each table."
        ::= { basicEntry 99 } 

    rsManufacturer OBJECT-TYPE
        SYNTAX DisplayString
        ACCESS read-only
        STATUS mandatory
        DESCRIPTION
            "The name of the RackSens manufacturer."
        ::= { basicEntry  1}

    rsUnitName OBJECT-TYPE
        SYNTAX DisplayString
        ACCESS read-only
        STATUS mandatory
        DESCRIPTION
            "The name of the RackSens unit."
        ::= { basicEntry 2}

    rsUnitVersion OBJECT-TYPE
        SYNTAX DisplayString
        ACCESS read-only
        STATUS mandatory
        DESCRIPTION
            "The version of the RackSens object table."
        ::= { basicEntry 3}

    rsObjectTableLoadingState OBJECT-TYPE
        SYNTAX INTEGER {
          notloaded(0),
          loading(1),
          loaded(2)
        }
        ACCESS read-only
        STATUS mandatory
        DESCRIPTION
            "The loading state of object table.
             0=table in not loaded
             1=table loading in process
             2=table is loaded"
        ::= { basicEntry 4}

    rsObjectTableEntries OBJECT-TYPE
        SYNTAX INTEGER 
        ACCESS read-only
        STATUS mandatory
        DESCRIPTION
            "The no. of objects in object table."
        ::= { basicEntry 5}

    rsObjectDataValid OBJECT-TYPE
        SYNTAX INTEGER {
          valid(0),
          invalid(1)
        }
        ACCESS read-only
        STATUS mandatory
        DESCRIPTION
            "The marker for invalid object data, set when object data is invalid."
        ::= { basicEntry 6}

    rsProcessData OBJECT-TYPE
        SYNTAX OCTET STRING
        ACCESS read-only
        STATUS mandatory
        DESCRIPTION
            "The actual state of the RackSens. It consists of 16 bit from which every
             one of them can be examined under id 1000 to 1015."
        ::= { basicEntry 100 }

    ----------------------------------------------------
    -- Bits from RackSens Process Data
    ----------------------------------------------------

    pswExtinguishing OBJECT-TYPE
        SYNTAX INTEGER {
            off(0),
            on(1)
        }
        ACCESS read-only
        STATUS mandatory
        DESCRIPTION
            "If one (1) the unit is extinguishing."
        ::= { basicEntry 1000 }

    pswCutOffActive OBJECT-TYPE
        SYNTAX INTEGER {
            inactive(0),
            active(1)
        }
        ACCESS read-only
        STATUS mandatory
        DESCRIPTION
            "If one (1) the unit has engaged its cut-off relay."
        ::= { basicEntry 1001 }

    pswManualActivation OBJECT-TYPE
        SYNTAX INTEGER {
            off(0),
            on(1)
        }
        ACCESS read-only
        STATUS mandatory
        DESCRIPTION
            "If one (1) the unit is manual activated."
        ::= { basicEntry 1002 }

    pswMainAlarmD1 OBJECT-TYPE
        SYNTAX INTEGER {
            off(0),
            on(1)
        }
        ACCESS read-only
        STATUS mandatory
        DESCRIPTION
            "If one (1) the detector 1 is in fire alarm state."
        ::= { basicEntry 1003 }

    pswMainAlarmD2 OBJECT-TYPE
        SYNTAX INTEGER {
            off(0),
            on(1)
        }
        ACCESS read-only
        STATUS mandatory
        DESCRIPTION
            "If one (1) the detector 2 is in fire alarm state."
        ::= { basicEntry 1004 }

    pswPreAlarmD1 OBJECT-TYPE
        SYNTAX INTEGER {
            off(0),
            on(1)
        }
        ACCESS read-only
        STATUS mandatory
        DESCRIPTION
            "If one (1) the detector 1 is in action alarm state."
        ::= { basicEntry 1005 }

    pswPreAlarmD2 OBJECT-TYPE
        SYNTAX INTEGER {
            off(0),
            on(1)
        }
        ACCESS read-only
        STATUS mandatory
        DESCRIPTION
            "If one (1) the detector 2 is in action alarm state."
        ::= { basicEntry 1006 }

    pswTemperatureAlarm1 OBJECT-TYPE
        SYNTAX INTEGER {
            off(0),
            on(1)
        }
        ACCESS read-only
        STATUS mandatory
        DESCRIPTION
            "If one (1) the temperature sensor 1 is in alarm state."
        ::= { basicEntry 1007 }

    pswTemperatureAlarm2 OBJECT-TYPE
        SYNTAX INTEGER {
            off(0),
            on(1)
        }
        ACCESS read-only
        STATUS mandatory
        DESCRIPTION
            "If one (1) the temperature sensor 2 is in alarm state."
        ::= { basicEntry 1008 }

    pswTemperatureAlarm3 OBJECT-TYPE
        SYNTAX INTEGER {
            off(0),
            on(1)
        }
        ACCESS read-only
        STATUS mandatory
        DESCRIPTION
            "If one (1) the temperature sensor 3 is in alarm state."
        ::= { basicEntry 1009 }

    pswTemperatureAlarm4 OBJECT-TYPE
        SYNTAX INTEGER {
            off(0),
            on(1)
        }
        ACCESS read-only
        STATUS mandatory
        DESCRIPTION
            "If one (1) the temperature sensor 4 is in alarm state."
        ::= { basicEntry 1010 }

    pswTemperatureAlarm5 OBJECT-TYPE
        SYNTAX INTEGER {
            off(0),
            on(1)
        }
        ACCESS read-only
        STATUS mandatory
        DESCRIPTION
            "If one (1) the temperature sensor 5 is in alarm state."
        ::= { basicEntry 1011 }

    pswFailure OBJECT-TYPE
        SYNTAX INTEGER {
            normal(0),
            failure(1)
        }
        ACCESS read-only
        STATUS mandatory
        DESCRIPTION
            "If one (1) the unit is failure state."
        ::= { basicEntry 1012 }

    pswServiceOrBlocked OBJECT-TYPE
        SYNTAX INTEGER {
            normal(0),
            blocked(1)
        }
        ACCESS read-only
        STATUS mandatory
        DESCRIPTION
            "If one (1) the unit is service or blocked state."
        ::= { basicEntry 1013 }

    pswDoorState OBJECT-TYPE
        SYNTAX INTEGER {
            closed(0),
            open(1)
        }
        ACCESS read-only
        STATUS mandatory
        DESCRIPTION
            "If one (1) the door of the rack is open."
        ::= { basicEntry 1014 }

    pswUnitMainAlarm OBJECT-TYPE
        SYNTAX INTEGER {
            off(0),
            alarm(1)
        }
        ACCESS read-only
        STATUS mandatory
        DESCRIPTION
            "If one (1) the unit is in fire alarm state."
        ::= { basicEntry 1015 }

END
