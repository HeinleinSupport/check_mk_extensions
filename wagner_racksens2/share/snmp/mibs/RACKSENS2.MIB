-- Software 0104.12.003
--
-- Changes:
--
-- 2011-02-11 EE/Le 
--   Descriptions reviewed.
--
-- 2011-01-11 EE/Le 
--   Trap definitions redefined.
--
-- 2010-12-20 EE/Le 
--   Object pswUnitMainAlarm was formerly misdeclared as pswAirFlowInit
-- 
-- Copyright (c) 2010, 2011
--
-- WAGNER Group GmbH
-- Schleswigstr. 1-5
-- 30853 Langenhagen
-- Germany
--

RACKSENS2-MIB DEFINITIONS ::= BEGIN

    IMPORTS 
        enterprises     FROM RFC1155-SMI
        OBJECT-TYPE     FROM RFC-1212
        DisplayString   FROM RFC1213-MIB
        TRAP-TYPE       FROM RFC-1215
        Gauge           FROM RFC1155-SMI
        Opaque          FROM RFC1155-SMI
        TimeTicks       FROM RFC1155-SMI;

    wagner          OBJECT IDENTIFIER ::= { enterprises 34187 }
    racksens2       OBJECT IDENTIFIER ::= { wagner      57949 }
    racksenstrap    OBJECT IDENTIFIER ::= { racksens2   3     }

    ----------------------------------------------------
    -- Traps
    ----------------------------------------------------

    pswExtinguishing-trap   TRAP-TYPE
        ENTERPRISE racksenstrap
        VARIABLES { pswExtinguishing }
        DESCRIPTION
            "Unit extinguishing state changed."
        ::= 1000

    pswCutOffActive-trap   TRAP-TYPE
        ENTERPRISE racksenstrap
        VARIABLES { pswCutOffActive }
        DESCRIPTION
            "Cut-off relay state changed."
        ::= 1001

    pswManualActivation-trap   TRAP-TYPE
        ENTERPRISE racksenstrap
        VARIABLES { pswManualActivation }
        DESCRIPTION
            "Manual activation state changed."
        ::= 1002

    pswMainAlarmD1-trap   TRAP-TYPE
        ENTERPRISE racksenstrap
        VARIABLES { pswMainAlarmD1 }
        DESCRIPTION
            "Detector 1 fire alarm state state changed."
        ::= 1003

    pswMainAlarmD2-trap   TRAP-TYPE
        ENTERPRISE racksenstrap
        VARIABLES { pswMainAlarmD2 }
        DESCRIPTION
            "Detector 2 fire alarm state state changed."
        ::= 1004

    pswPreAlarmD1-trap   TRAP-TYPE
        ENTERPRISE racksenstrap
        VARIABLES { pswPreAlarmD1 }
        DESCRIPTION
            "Detector 1 action alarm state state changed."
        ::= 1005

    pswPreAlarmD2-trap   TRAP-TYPE
        ENTERPRISE racksenstrap
        VARIABLES { pswPreAlarmD2 }
        DESCRIPTION
            "Detector 2 action alarm state state changed."
        ::= 1006

    pswTemperatureAlarm1-trap   TRAP-TYPE
        ENTERPRISE racksenstrap
        VARIABLES { pswTemperatureAlarm1 }
        DESCRIPTION
            "Temperature sensor 1 alarm state state changed."
        ::= 1007

    pswTemperatureAlarm2-trap   TRAP-TYPE
        ENTERPRISE racksenstrap
        VARIABLES { pswTemperatureAlarm2 }
        DESCRIPTION
            "Temperature sensor 2 alarm state state changed."
        ::= 1008

    pswTemperatureAlarm3-trap   TRAP-TYPE
        ENTERPRISE racksenstrap
        VARIABLES { pswTemperatureAlarm3 }
        DESCRIPTION
            "Temperature sensor 3 alarm state state changed."
        ::= 1009

    pswTemperatureAlarm4-trap   TRAP-TYPE
        ENTERPRISE racksenstrap
        VARIABLES { pswTemperatureAlarm4 }
        DESCRIPTION
            "Temperature sensor 4 alarm state state changed."
        ::= 1010

    pswTemperatureAlarm5-trap   TRAP-TYPE
        ENTERPRISE racksenstrap
        VARIABLES { pswTemperatureAlarm5 }
        DESCRIPTION
            "Temperature sensor 5 alarm state state changed."
        ::= 1011

    pswFailure-trap   TRAP-TYPE
        ENTERPRISE racksenstrap
        VARIABLES { pswFailure }
        DESCRIPTION
            "Failure state changed."
        ::= 1012

    pswServiceOrBlocked-trap   TRAP-TYPE
        ENTERPRISE racksenstrap
        VARIABLES { pswServiceOrBlocked }
        DESCRIPTION
            "Blocked state changed."
        ::= 1013

    pswDoorState-trap   TRAP-TYPE
        ENTERPRISE racksenstrap
        VARIABLES { pswDoorState }
        DESCRIPTION
            "Door open state changed."
        ::= 1014

    pswUnitMainAlarm-trap   TRAP-TYPE
        ENTERPRISE racksenstrap
        VARIABLES { pswUnitMainAlarm }
        DESCRIPTION
            "Unit fire alarm state changed."
        ::= 1015

    ----------------------------------------------------
    ----------------------------------------------------

    basicTable OBJECT-TYPE
        SYNTAX SEQUENCE OF BasicEntry
        ACCESS not-accessible
        STATUS mandatory
        ::= { racksens2 1 }

    basicEntry OBJECT-TYPE
        SYNTAX BasicEntry
        ACCESS not-accessible
        STATUS mandatory
        DESCRIPTION
            "This is the table for basic entries!"
        INDEX { basicIndex }
        ::= { basicTable 1 }

    BasicEntry ::= SEQUENCE {
        basicIndex                  INTEGER,
        rsManufacturer              DisplayString,
        rsUnitName                  DisplayString,
        rsUnitVersion               DisplayString,
        rsObjectTableLoadingState   INTEGER,
        rsObjectTableEntries        INTEGER,
        rsObjectDataValid           INTEGER,
        rsProcessData               OCTET STRING,
        
        -- Process data bits
        
        pswExtinguishing            INTEGER,
        pswCutOffActive             INTEGER,
        pswManualActivation         INTEGER,
        pswMainAlarmD1              INTEGER,
        pswMainAlarmD2              INTEGER,
        pswPreAlarmD1               INTEGER,
        pswPreAlarmD2               INTEGER,
        pswTemperatureAlarm1        INTEGER,
        pswTemperatureAlarm2        INTEGER,
        pswTemperatureAlarm3        INTEGER,
        pswTemperatureAlarm4        INTEGER,
        pswTemperatureAlarm5        INTEGER,
        pswFailure                  INTEGER,
        pswServiceOrBlocked         INTEGER,
        pswDoorState                INTEGER,
        pswUnitMainAlarm            INTEGER
    }

    ----------------------------------------------------
    -- RackSens basic data
    ----------------------------------------------------

    basicIndex OBJECT-TYPE
        SYNTAX  INTEGER (0..1)
        ACCESS  read-only
        STATUS  mandatory
        DESCRIPTION
                "A unique value for each table."
        ::= { basicEntry 99 } 

    rsManufacturer OBJECT-TYPE
        SYNTAX DisplayString
        ACCESS read-only
        STATUS mandatory
        DESCRIPTION
            "The name of the RackSens manufacturer."
        ::= { basicEntry  1}

    rsUnitName OBJECT-TYPE
        SYNTAX DisplayString
        ACCESS read-only
        STATUS mandatory
        DESCRIPTION
            "The name of the RackSens unit."
        ::= { basicEntry 2}

    rsUnitVersion OBJECT-TYPE
        SYNTAX DisplayString
        ACCESS read-only
        STATUS mandatory
        DESCRIPTION
            "The version of the RackSens object table."
        ::= { basicEntry 3}

    rsObjectTableLoadingState OBJECT-TYPE
        SYNTAX INTEGER {
          notloaded(0),
          loading(1),
          loaded(2)
        }
        ACCESS read-only
        STATUS mandatory
        DESCRIPTION
            "The loading state of object table.
             0=table in not loaded
             1=table loading in process
             2=table is loaded"
        ::= { basicEntry 4}

    rsObjectTableEntries OBJECT-TYPE
        SYNTAX INTEGER 
        ACCESS read-only
        STATUS mandatory
        DESCRIPTION
            "The no. of objects in object table."
        ::= { basicEntry 5}

    rsObjectDataValid OBJECT-TYPE
        SYNTAX INTEGER {
          valid(0),
          invalid(1)
        }
        ACCESS read-only
        STATUS mandatory
        DESCRIPTION
            "The marker for invalid object data, set when object data is invalid."
        ::= { basicEntry 6}

    rsProcessData OBJECT-TYPE
        SYNTAX OCTET STRING
        ACCESS read-only
        STATUS mandatory
        DESCRIPTION
            "The actual state of the RackSens. It consists of 16 bit from which every
             one of them can be examined under id 1000 to 1015."
        ::= { basicEntry 100 }

    ----------------------------------------------------
    -- Bits from RackSens Process Data
    ----------------------------------------------------

    pswExtinguishing OBJECT-TYPE
        SYNTAX INTEGER {
            off(0),
            on(1)
        }
        ACCESS read-only
        STATUS mandatory
        DESCRIPTION
            "If one (1) the unit is extinguishing."
        ::= { basicEntry 1000 }

    pswCutOffActive OBJECT-TYPE
        SYNTAX INTEGER {
            inactive(0),
            active(1)
        }
        ACCESS read-only
        STATUS mandatory
        DESCRIPTION
            "If one (1) the unit has engaged its cut-off relay."
        ::= { basicEntry 1001 }

    pswManualActivation OBJECT-TYPE
        SYNTAX INTEGER {
            off(0),
            on(1)
        }
        ACCESS read-only
        STATUS mandatory
        DESCRIPTION
            "If one (1) the unit is manual activated."
        ::= { basicEntry 1002 }

    pswMainAlarmD1 OBJECT-TYPE
        SYNTAX INTEGER {
            off(0),
            on(1)
        }
        ACCESS read-only
        STATUS mandatory
        DESCRIPTION
            "If one (1) the detector 1 is in fire alarm state."
        ::= { basicEntry 1003 }

    pswMainAlarmD2 OBJECT-TYPE
        SYNTAX INTEGER {
            off(0),
            on(1)
        }
        ACCESS read-only
        STATUS mandatory
        DESCRIPTION
            "If one (1) the detector 2 is in fire alarm state."
        ::= { basicEntry 1004 }

    pswPreAlarmD1 OBJECT-TYPE
        SYNTAX INTEGER {
            off(0),
            on(1)
        }
        ACCESS read-only
        STATUS mandatory
        DESCRIPTION
            "If one (1) the detector 1 is in action alarm state."
        ::= { basicEntry 1005 }

    pswPreAlarmD2 OBJECT-TYPE
        SYNTAX INTEGER {
            off(0),
            on(1)
        }
        ACCESS read-only
        STATUS mandatory
        DESCRIPTION
            "If one (1) the detector 2 is in action alarm state."
        ::= { basicEntry 1006 }

    pswTemperatureAlarm1 OBJECT-TYPE
        SYNTAX INTEGER {
            off(0),
            on(1)
        }
        ACCESS read-only
        STATUS mandatory
        DESCRIPTION
            "If one (1) the temperature sensor 1 is in alarm state."
        ::= { basicEntry 1007 }

    pswTemperatureAlarm2 OBJECT-TYPE
        SYNTAX INTEGER {
            off(0),
            on(1)
        }
        ACCESS read-only
        STATUS mandatory
        DESCRIPTION
            "If one (1) the temperature sensor 2 is in alarm state."
        ::= { basicEntry 1008 }

    pswTemperatureAlarm3 OBJECT-TYPE
        SYNTAX INTEGER {
            off(0),
            on(1)
        }
        ACCESS read-only
        STATUS mandatory
        DESCRIPTION
            "If one (1) the temperature sensor 3 is in alarm state."
        ::= { basicEntry 1009 }

    pswTemperatureAlarm4 OBJECT-TYPE
        SYNTAX INTEGER {
            off(0),
            on(1)
        }
        ACCESS read-only
        STATUS mandatory
        DESCRIPTION
            "If one (1) the temperature sensor 4 is in alarm state."
        ::= { basicEntry 1010 }

    pswTemperatureAlarm5 OBJECT-TYPE
        SYNTAX INTEGER {
            off(0),
            on(1)
        }
        ACCESS read-only
        STATUS mandatory
        DESCRIPTION
            "If one (1) the temperature sensor 5 is in alarm state."
        ::= { basicEntry 1011 }

    pswFailure OBJECT-TYPE
        SYNTAX INTEGER {
            normal(0),
            failure(1)
        }
        ACCESS read-only
        STATUS mandatory
        DESCRIPTION
            "If one (1) the unit is failure state."
        ::= { basicEntry 1012 }

    pswServiceOrBlocked OBJECT-TYPE
        SYNTAX INTEGER {
            normal(0),
            blocked(1)
        }
        ACCESS read-only
        STATUS mandatory
        DESCRIPTION
            "If one (1) the unit is service or blocked state."
        ::= { basicEntry 1013 }

    pswDoorState OBJECT-TYPE
        SYNTAX INTEGER {
            closed(0),
            open(1)
        }
        ACCESS read-only
        STATUS mandatory
        DESCRIPTION
            "If one (1) the door of the rack is open."
        ::= { basicEntry 1014 }

    pswUnitMainAlarm OBJECT-TYPE
        SYNTAX INTEGER {
            off(0),
            initializing(1)
        }
        ACCESS read-only
        STATUS mandatory
        DESCRIPTION
            "If one (1) the unit is in fire alarm state."
        ::= { basicEntry 1015 }

    ----------------------------------------------------
    -- Object table
    ----------------------------------------------------

    objectTable OBJECT-TYPE
        SYNTAX SEQUENCE OF ObjectEntry
        ACCESS not-accessible
        STATUS mandatory
        ::= { racksens2 2 }

    objectEntry OBJECT-TYPE
        SYNTAX ObjectEntry
        ACCESS not-accessible
        STATUS mandatory
        DESCRIPTION
            "This is the table for object entries!"
        INDEX { objectIndex }
        ::= { objectTable 1}

    ObjectEntry ::= SEQUENCE {
        objectIndex                 INTEGER,
        rsUnitState                 OCTET STRING,
        rsUnitSerialNumber          INTEGER,
        rsDetector1SerialNumber     INTEGER,
        rsDetector2SerialNumber     INTEGER,
        rsTemperature1              Opaque,
        rsTemperature2              Opaque,
        rsTemperature3              Opaque,
        rsTemperature4              Opaque,
        rsTemperature5              Opaque,
        rsAirTemperature            Opaque,
        rsAirFlow                   Opaque,
        rsAirFlowdeviation          INTEGER,
        rsFirePlace                 INTEGER,
        rsDisplayData               OCTET STRING,
        rsStateInfo                 OCTET STRING,
        
        -- Smoke detector data
        
        rsMainAlarmThreshold1       INTEGER,
        rsPreAlarmThreshold1        INTEGER,
        rsBargraphLevel1            INTEGER,
        rsSmokeLevel1               Opaque,
        rsChamberState1             INTEGER,
        rsMainAlarmThreshold2       INTEGER,
        rsPreAlarmThreshold2        INTEGER,
        rsBargraphLevel2            INTEGER,
        rsSmokeLevel2               Opaque,
        rsChamberState2             INTEGER,
    
        -- Adjustments
        
        rsAlarmDelayTime            INTEGER,
        rsAirFlowFailureThreshold   INTEGER,
        rsAirFlowFailureDelayTime   INTEGER,
        rsExtinguishPreWarnTime     INTEGER,
        rsDetector1Sensibility      Opaque,
        rsDetector2Sensibility      Opaque,
        rsAlarmTemperatureSensor1   Opaque,
        rsAlarmTemperatureSensor2   Opaque,
        rsAlarmTemperatureSensor3   Opaque,
        rsAlarmTemperatureSensor4   Opaque,
        rsAlarmTemperatureSensor5   Opaque,
        rsFanVoltage                Opaque,
        
        -- Bus element 1..10
        
        rsBusUnit01SerialNumber     INTEGER,
        rsBusUnit02SerialNumber     INTEGER,
        rsBusUnit03SerialNumber     INTEGER,
        rsBusUnit04SerialNumber     INTEGER,
        rsBusUnit05SerialNumber     INTEGER,
        rsBusUnit06SerialNumber     INTEGER,
        rsBusUnit07SerialNumber     INTEGER,
        rsBusUnit08SerialNumber     INTEGER,
        rsBusUnit09SerialNumber     INTEGER,
        rsBusUnit10SerialNumber     INTEGER,
        rsBusUnitStateInfo          OCTET STRING,
        rsBusUnitDisplayData        OCTET STRING,
        
        -- Reset control data
        
        rsResetControl              OCTET STRING,

        -- Flow reference

		rsFlowReference				Opaque,

        -- Unit state bits

        rsExtinguishing             INTEGER,
        rsCutOffActive              INTEGER,
        rsManualActivation          INTEGER,
        rsMainAlarmD1               INTEGER,
        rsMainAlarmD2               INTEGER,
        rsPreAlarmD1                INTEGER,
        rsPreAlarmD2                INTEGER,
        rsTemperatureAlarm1         INTEGER,
        rsTemperatureAlarm2         INTEGER,
        rsTemperatureAlarm3         INTEGER,
        rsTemperatureAlarm4         INTEGER,
        rsTemperatureAlarm5         INTEGER,
        rsFailure                   INTEGER,
        rsServiceOrBlocked          INTEGER,
        rsDoorState                 INTEGER,
        rsAirFlowInit               INTEGER,

        -- Display data bits
        
        rsServiceDisplayBlinking                INTEGER,
        rsServiceDisplayOn                      INTEGER,
        rsMainsDisplayBlinking                  INTEGER,
        rsMainsDisplayOn                        INTEGER,
        rsBatteryDisplayBlinking                INTEGER,
        rsBatteryDisplayOn                      INTEGER,
        rsFailureDisplayBlinking                INTEGER,
        rsFailureDisplayOn                      INTEGER,
        rsManualActivationDisplayBlinking       INTEGER,
        rsManualActivationDisplayOn             INTEGER,
        rsAlarmDisplayBlinking                  INTEGER,
        rsAlarmDisplayOn                        INTEGER,
        rsOperatingDisplayBlinking              INTEGER,
        rsOperatingDisplayOn                    INTEGER,
        rsActivatedDisplayBlinking              INTEGER,
        rsActivatedDisplayOn                    INTEGER,
        rsDetector2PreAlarmDisplayBlinking      INTEGER,
        rsDetector2PreAlarmDisplayOn            INTEGER,
        rsDetector1PreAlarmDisplayBlinking      INTEGER,
        rsDetector1PreAlarmDisplayOn            INTEGER,
        rsDetector2MainAlarmDisplayBlinking     INTEGER,
        rsDetector2MainAlarmDisplayOn           INTEGER,
        rsDetector1MainAlarmDisplayBlinking     INTEGER,
        rsDetector1MainAlarmDisplayOn           INTEGER,
        
        -- State info bits

        rsDoorContact               INTEGER,
        rsFailureRelay              INTEGER,
        rsServiceBlockedRelay       INTEGER,
        rsActivatedRelay            INTEGER,
        rsMainAlarm1Relay           INTEGER,
        rsMainAlarm2Relay           INTEGER,
        rsPreAlarm1Relay            INTEGER,
        rsPreAlarm2Relay            INTEGER,
        rsProgrammableRelay1        INTEGER,
        rsProgrammableRelay2        INTEGER,
        rsProgrammableRelay3        INTEGER,
        rsProgrammableRelay4        INTEGER,
        rsProgrammableRelay5        INTEGER,
        rsTemperatureAlarm1State    INTEGER,
        rsTemperatureAlarm2State    INTEGER,
        rsTemperatureAlarm3State    INTEGER,
        rsTemperatureAlarm4State    INTEGER,
        rsTemperatureAlarm5State    INTEGER,
        rsBuzzerState               INTEGER,
        rsFailureStorage            INTEGER,
        rsDynamicAirFlowControl     INTEGER,
        rsAirFlowInitState          INTEGER,
        rsRoomIdentState            INTEGER,
        rsMainAlarmAfterRoomIdent   INTEGER,
        rsLogicSensDetector1State   INTEGER,
        rsLogicSensDetector2State   INTEGER,
        rsDetectorBox2Registrated   INTEGER,
        rsBusUnit1Registrated       INTEGER,
        rsBusUnit2Registrated       INTEGER,
        rsBusUnit3Registrated       INTEGER,
        rsBusUnit4Registrated       INTEGER,
        rsBusUnit5Registrated       INTEGER,
        rsBusUnit6Registrated       INTEGER,
        rsBusUnit7Registrated       INTEGER,
        rsBusUnit8Registrated       INTEGER,
        rsBusUnit9Registrated       INTEGER,
        rsBusUnit10Registrated      INTEGER,
        rsTempSensor1Registrated    INTEGER,
        rsTempSensor2Registrated    INTEGER,
        rsTempSensor3Registrated    INTEGER,
        rsTempSensor4Registrated    INTEGER,
        rsTempSensor5Registrated    INTEGER,
        rsAirFlowControlAvailable   INTEGER,
        rsDynFlowControlAvailable   INTEGER,
        rsBatteryLoaderAvailable    INTEGER,
        rsPreAlarmDisplayAvailable  INTEGER,
        rsBargraphAvailable         INTEGER,
        rsRoomIdentAvailable        INTEGER,
        rsLogicSensDet1Available    INTEGER,
        rsLogicSensDet2Available    INTEGER,
        rsTempSensorsAvailable      INTEGER,
        rsProgRelaysAvailable       INTEGER,

        rsUnitBlocked                   INTEGER,
        rsUnitIsolated                  INTEGER,
        rsSupplyVoltageLow              INTEGER,
        rsProgramFailure                INTEGER,
        rsFanControlFailure             INTEGER,
        rsTempSensorFailure             INTEGER,
        rsBatteryFailure                INTEGER,
        rsMainsSupplyFailure            INTEGER,
        rsManualActLineFailure          INTEGER,
        rsTooManyBusUnits               INTEGER,
        rsBusUnitFailure                INTEGER,
        rsAgentLoss                     INTEGER,
        rsBusFailure                    INTEGER,
        rsNetworkFailure                INTEGER,
        rsDetector1CommunicationFailure INTEGER,
        rsDetector1Failure              INTEGER,
        rsChamber1Dirty                 INTEGER,
        rsAirFlowControlFailure         INTEGER,
        rsStaticAirFlowLow              INTEGER,
        rsStaticAirFlowHigh             INTEGER,
        rsDynamicAirFlowLow             INTEGER,
        rsDynamicAirFlowHigh            INTEGER,
        rsAirFlowInitAborted            INTEGER,
        rsRoomIdentFailure              INTEGER,
        rsDetector2CommunicationFailure INTEGER,
        rsDetector2Failure              INTEGER,
        rsChamber2Dirty                 INTEGER,

        rsUnitBlockedStored                     INTEGER,
        rsUnitIsolatedStored                    INTEGER,
        rsSupplyVoltageLowStored                INTEGER,
        rsProgramFailureStored                  INTEGER,
        rsFanControlFailureStored               INTEGER,
        rsTempSensorFailureStored               INTEGER,
        rsBatteryFailureStored                  INTEGER,
        rsMainsSupplyFailureStored              INTEGER,
        rsManualActLineFailureStored            INTEGER,
        rsTooManyBusUnitsStored                 INTEGER,
        rsBusUnitFailureStored                  INTEGER,
        rsAgentLossStored                       INTEGER,
        rsBusFailureStored                      INTEGER,
        rsNetworkFailureStored                  INTEGER,
        rsDetector1CommunicationFailureStored   INTEGER,
        rsDetector1FailureStored                INTEGER,
        rsChamber1DirtyStored                   INTEGER,
        rsAirFlowControlFailureStored           INTEGER,
        rsStaticAirFlowLowStored                INTEGER,
        rsStaticAirFlowHighStored               INTEGER,
        rsDynamicAirFlowLowStored               INTEGER,
        rsDynamicAirFlowHighStored              INTEGER,
        rsAirFlowInitAbortedStored              INTEGER,
        rsRoomIdentFailureStored                INTEGER,
        rsDetector2CommunicationFailureStored   INTEGER,
        rsDetector2FailureStored                INTEGER,
        rsChamber2DirtyStored                   INTEGER,

        rsUnitBlockedValid                      INTEGER,
        rsUnitIsolatedValid                     INTEGER,
        rsSupplyVoltageLowValid                 INTEGER,
        rsProgramFailureValid                   INTEGER,
        rsFanControlFailureValid                INTEGER,
        rsTempSensorFailureValid                INTEGER,
        rsBatteryFailureValid                   INTEGER,
        rsMainsSupplyFailureValid               INTEGER,
        rsManualActLineFailureValid             INTEGER,
        rsTooManyBusUnitsValid                  INTEGER,
        rsBusUnitFailureValid                   INTEGER,
        rsAgentLossValid                        INTEGER,
        rsBusFailureValid                       INTEGER,
        rsNetworkFailureValid                   INTEGER,
        rsDetector1CommunicationFailureValid    INTEGER,
        rsDetector1FailureValid                 INTEGER,
        rsChamber1DirtyValid                    INTEGER,
        rsAirFlowControlFailureValid            INTEGER,
        rsStaticAirFlowLowValid                 INTEGER,
        rsStaticAirFlowHighValid                INTEGER,
        rsDynamicAirFlowLowValid                INTEGER,
        rsDynamicAirFlowHighValid               INTEGER,
        rsAirFlowInitAbortedValid               INTEGER,
        rsRoomIdentFailureValid                 INTEGER,
        rsDetector2CommunicationFailureValid    INTEGER,
        rsDetector2FailureValid                 INTEGER,
        rsChamber2DirtyValid                    INTEGER,

        rsTempSensor1Failure            INTEGER,
        rsTempSensor2Failure            INTEGER,
        rsTempSensor3Failure            INTEGER,
        rsTempSensor4Failure            INTEGER,
        rsTempSensor5Failure            INTEGER,
        rsUnitHasInternalExtModule      INTEGER,
        rsInternalExtModuleLacksValid   INTEGER,
        rsInternalExtModuleLacks        INTEGER,
        rsInternalExtModuleLacksStored  INTEGER,
        rsManualActivated               INTEGER,
        rsMainAlarmSet                  INTEGER,
                
        -- Bus unit 1..10 state info bits
        
        rsBU01DoorSwitchExists              INTEGER,
        rsBU01ManualActivationLineExists    INTEGER,
        rsBU01CutOffRelayExists             INTEGER,
        rsBU01IgnitionLineExists            INTEGER,
        
        rsBU02DoorSwitchExists              INTEGER,
        rsBU02ManualActivationLineExists    INTEGER,
        rsBU02CutOffRelayExists             INTEGER,
        rsBU02IgnitionLineExists            INTEGER,
        
        rsBU03DoorSwitchExists              INTEGER,
        rsBU03ManualActivationLineExists    INTEGER,
        rsBU03CutOffRelayExists             INTEGER,
        rsBU03IgnitionLineExists            INTEGER,
        
        rsBU04DoorSwitchExists              INTEGER,
        rsBU04ManualActivationLineExists    INTEGER,
        rsBU04CutOffRelayExists             INTEGER,
        rsBU04IgnitionLineExists            INTEGER,
        
        rsBU05DoorSwitchExists              INTEGER,
        rsBU05ManualActivationLineExists    INTEGER,
        rsBU05CutOffRelayExists             INTEGER,
        rsBU05IgnitionLineExists            INTEGER,
        
        rsBU06DoorSwitchExists              INTEGER,
        rsBU06ManualActivationLineExists    INTEGER,
        rsBU06CutOffRelayExists             INTEGER,
        rsBU06IgnitionLineExists            INTEGER,
        
        rsBU07DoorSwitchExists              INTEGER,
        rsBU07ManualActivationLineExists    INTEGER,
        rsBU07CutOffRelayExists             INTEGER,
        rsBU07IgnitionLineExists            INTEGER,
        
        rsBU08DoorSwitchExists              INTEGER,
        rsBU08ManualActivationLineExists    INTEGER,
        rsBU08CutOffRelayExists             INTEGER,
        rsBU08IgnitionLineExists            INTEGER,
        
        rsBU09DoorSwitchExists              INTEGER,
        rsBU09ManualActivationLineExists    INTEGER,
        rsBU09CutOffRelayExists             INTEGER,
        rsBU09IgnitionLineExists            INTEGER,
        
        rsBU10DoorSwitchExists              INTEGER,
        rsBU10ManualActivationLineExists    INTEGER,
        rsBU10CutOffRelayExists             INTEGER,
        rsBU10IgnitionLineExists            INTEGER,
        
        rsBU01ProgramFailure                INTEGER,
        rsBU01AgentLoss                     INTEGER,
        rsBU01SupplyVoltageLow              INTEGER,
        rsBU01IgnitionVoltageLow            INTEGER,
        rsBU01CutOffLineFailure             INTEGER,
        rsBU01IgnitionLineFailure           INTEGER,
        rsBU01ManActivationLineFailure      INTEGER,
        rsBU01Failure                       INTEGER,
        
        rsBU02ProgramFailure                INTEGER,
        rsBU02AgentLoss                     INTEGER,
        rsBU02SupplyVoltageLow              INTEGER,
        rsBU02IgnitionVoltageLow            INTEGER,
        rsBU02CutOffLineFailure             INTEGER,
        rsBU02IgnitionLineFailure           INTEGER,
        rsBU02ManActivationLineFailure      INTEGER,
        rsBU02Failure                       INTEGER,
        
        rsBU03ProgramFailure                INTEGER,
        rsBU03AgentLoss                     INTEGER,
        rsBU03SupplyVoltageLow              INTEGER,
        rsBU03IgnitionVoltageLow            INTEGER,
        rsBU03CutOffLineFailure             INTEGER,
        rsBU03IgnitionLineFailure           INTEGER,
        rsBU03ManActivationLineFailure      INTEGER,
        rsBU03Failure                       INTEGER,
        
        rsBU04ProgramFailure                INTEGER,
        rsBU04AgentLoss                     INTEGER,
        rsBU04SupplyVoltageLow              INTEGER,
        rsBU04IgnitionVoltageLow            INTEGER,
        rsBU04CutOffLineFailure             INTEGER,
        rsBU04IgnitionLineFailure           INTEGER,
        rsBU04ManActivationLineFailure      INTEGER,
        rsBU04Failure                       INTEGER,
        
        rsBU05ProgramFailure                INTEGER,
        rsBU05AgentLoss                     INTEGER,
        rsBU05SupplyVoltageLow              INTEGER,
        rsBU05IgnitionVoltageLow            INTEGER,
        rsBU05CutOffLineFailure             INTEGER,
        rsBU05IgnitionLineFailure           INTEGER,
        rsBU05ManActivationLineFailure      INTEGER,
        rsBU05Failure                       INTEGER,
        
        rsBU06ProgramFailure                INTEGER,
        rsBU06AgentLoss                     INTEGER,
        rsBU06SupplyVoltageLow              INTEGER,
        rsBU06IgnitionVoltageLow            INTEGER,
        rsBU06CutOffLineFailure             INTEGER,
        rsBU06IgnitionLineFailure           INTEGER,
        rsBU06ManActivationLineFailure      INTEGER,
        rsBU06Failure                       INTEGER,
        
        rsBU07ProgramFailure                INTEGER,
        rsBU07AgentLoss                     INTEGER,
        rsBU07SupplyVoltageLow              INTEGER,
        rsBU07IgnitionVoltageLow            INTEGER,
        rsBU07CutOffLineFailure             INTEGER,
        rsBU07IgnitionLineFailure           INTEGER,
        rsBU07ManActivationLineFailure      INTEGER,
        rsBU07Failure                       INTEGER,
        
        rsBU08ProgramFailure                INTEGER,
        rsBU08AgentLoss                     INTEGER,
        rsBU08SupplyVoltageLow              INTEGER,
        rsBU08IgnitionVoltageLow            INTEGER,
        rsBU08CutOffLineFailure             INTEGER,
        rsBU08IgnitionLineFailure           INTEGER,
        rsBU08ManActivationLineFailure      INTEGER,
        rsBU08Failure                       INTEGER,
        
        rsBU09ProgramFailure                INTEGER,
        rsBU09AgentLoss                     INTEGER,
        rsBU09SupplyVoltageLow              INTEGER,
        rsBU09IgnitionVoltageLow            INTEGER,
        rsBU09CutOffLineFailure             INTEGER,
        rsBU09IgnitionLineFailure           INTEGER,
        rsBU09ManActivationLineFailure      INTEGER,
        rsBU09Failure                       INTEGER,
        
        rsBU10ProgramFailure                INTEGER,
        rsBU10AgentLoss                     INTEGER,
        rsBU10SupplyVoltageLow              INTEGER,
        rsBU10IgnitionVoltageLow            INTEGER,
        rsBU10CutOffLineFailure             INTEGER,
        rsBU10IgnitionLineFailure           INTEGER,
        rsBU10ManActivationLineFailure      INTEGER,
        rsBU10Failure                       INTEGER,
        
        rsBU01ProgramFailureStored              INTEGER,
        rsBU01AgentLossStored                   INTEGER,
        rsBU01SupplyVoltageLowStored            INTEGER,
        rsBU01IgnitionVoltageLowStored          INTEGER,
        rsBU01CutOffLineFailureStored           INTEGER,
        rsBU01IgnitionLineFailureStored         INTEGER,
        rsBU01ManActivationLineFailureStored    INTEGER,
        rsBU01FailureStored                     INTEGER,
        
        rsBU02ProgramFailureStored              INTEGER,
        rsBU02AgentLossStored                   INTEGER,
        rsBU02SupplyVoltageLowStored            INTEGER,
        rsBU02IgnitionVoltageLowStored          INTEGER,
        rsBU02CutOffLineFailureStored           INTEGER,
        rsBU02IgnitionLineFailureStored         INTEGER,
        rsBU02ManActivationLineFailureStored    INTEGER,
        rsBU02FailureStored                     INTEGER,
        
        rsBU03ProgramFailureStored              INTEGER,
        rsBU03AgentLossStored                   INTEGER,
        rsBU03SupplyVoltageLowStored            INTEGER,
        rsBU03IgnitionVoltageLowStored          INTEGER,
        rsBU03CutOffLineFailureStored           INTEGER,
        rsBU03IgnitionLineFailureStored         INTEGER,
        rsBU03ManActivationLineFailureStored    INTEGER,
        rsBU03FailureStored                     INTEGER,
        
        rsBU04ProgramFailureStored              INTEGER,
        rsBU04AgentLossStored                   INTEGER,
        rsBU04SupplyVoltageLowStored            INTEGER,
        rsBU04IgnitionVoltageLowStored          INTEGER,
        rsBU04CutOffLineFailureStored           INTEGER,
        rsBU04IgnitionLineFailureStored         INTEGER,
        rsBU04ManActivationLineFailureStored    INTEGER,
        rsBU04FailureStored                     INTEGER,
        
        rsBU05ProgramFailureStored              INTEGER,
        rsBU05AgentLossStored                   INTEGER,
        rsBU05SupplyVoltageLowStored            INTEGER,
        rsBU05IgnitionVoltageLowStored          INTEGER,
        rsBU05CutOffLineFailureStored           INTEGER,
        rsBU05IgnitionLineFailureStored         INTEGER,
        rsBU05ManActivationLineFailureStored    INTEGER,
        rsBU05FailureStored                     INTEGER,
        
        rsBU06ProgramFailureStored              INTEGER,
        rsBU06AgentLossStored                   INTEGER,
        rsBU06SupplyVoltageLowStored            INTEGER,
        rsBU06IgnitionVoltageLowStored          INTEGER,
        rsBU06CutOffLineFailureStored           INTEGER,
        rsBU06IgnitionLineFailureStored         INTEGER,
        rsBU06ManActivationLineFailureStored    INTEGER,
        rsBU06FailureStored                     INTEGER,
        
        rsBU07ProgramFailureStored              INTEGER,
        rsBU07AgentLossStored                   INTEGER,
        rsBU07SupplyVoltageLowStored            INTEGER,
        rsBU07IgnitionVoltageLowStored          INTEGER,
        rsBU07CutOffLineFailureStored           INTEGER,
        rsBU07IgnitionLineFailureStored         INTEGER,
        rsBU07ManActivationLineFailureStored    INTEGER,
        rsBU07FailureStored                     INTEGER,
        
        rsBU08ProgramFailureStored              INTEGER,
        rsBU08AgentLossStored                   INTEGER,
        rsBU08SupplyVoltageLowStored            INTEGER,
        rsBU08IgnitionVoltageLowStored          INTEGER,
        rsBU08CutOffLineFailureStored           INTEGER,
        rsBU08IgnitionLineFailureStored         INTEGER,
        rsBU08ManActivationLineFailureStored    INTEGER,
        rsBU08FailureStored                     INTEGER,
        
        rsBU09ProgramFailureStored              INTEGER,
        rsBU09AgentLossStored                   INTEGER,
        rsBU09SupplyVoltageLowStored            INTEGER,
        rsBU09IgnitionVoltageLowStored          INTEGER,
        rsBU09CutOffLineFailureStored           INTEGER,
        rsBU09IgnitionLineFailureStored         INTEGER,
        rsBU09ManActivationLineFailureStored    INTEGER,
        rsBU09FailureStored                     INTEGER,
        
        rsBU10ProgramFailureStored              INTEGER,
        rsBU10AgentLossStored                   INTEGER,
        rsBU10SupplyVoltageLowStored            INTEGER,
        rsBU10IgnitionVoltageLowStored          INTEGER,
        rsBU10CutOffLineFailureStored           INTEGER,
        rsBU10IgnitionLineFailureStored         INTEGER,
        rsBU10ManActivationLineFailureStored    INTEGER,
        rsBU10FailureStored                     INTEGER,
        
        -- Bus unit 1..10 display data bits

        rsBU01ActivatedDisplayBlinking          INTEGER,
        rsBU01ActivatedDisplayOn                INTEGER,
        rsBU01ServiceDisplayBlinking            INTEGER,
        rsBU01ServiceDisplayOn                  INTEGER,
        rsBU01FailureDisplayBlinking            INTEGER,
        rsBU01FailureDisplayOn                  INTEGER,
        rsBU01OperatingDisplayBlinking          INTEGER,
        rsBU01OperatingDisplayOn                INTEGER,
        rsBU01ManualActivationDisplayBlinking   INTEGER,
        rsBU01ManualActivationDisplayOn         INTEGER,
        rsBU01OnlineDisplayDisplayOn            INTEGER,
        rsBU01IgnitionLineActivatedDisplayOn    INTEGER,
        rsBU01CutOffLineActivatedDisplayOn      INTEGER,
        rsBU01DoorSwitchDisplayOn               INTEGER,
        rsBU01Bit14                             INTEGER,
        rsBU01Bit15                             INTEGER,
        
        rsBU02ActivatedDisplayBlinking          INTEGER,
        rsBU02ActivatedDisplayOn                INTEGER,
        rsBU02ServiceDisplayBlinking            INTEGER,
        rsBU02ServiceDisplayOn                  INTEGER,
        rsBU02FailureDisplayBlinking            INTEGER,
        rsBU02FailureDisplayOn                  INTEGER,
        rsBU02OperatingDisplayBlinking          INTEGER,
        rsBU02OperatingDisplayOn                INTEGER,
        rsBU02ManualActivationDisplayBlinking   INTEGER,
        rsBU02ManualActivationDisplayOn         INTEGER,
        rsBU02OnlineDisplayDisplayOn            INTEGER,
        rsBU02IgnitionLineActivatedDisplayOn    INTEGER,
        rsBU02CutOffLineActivatedDisplayOn      INTEGER,
        rsBU02DoorSwitchDisplayOn               INTEGER,
        rsBU02Bit14                             INTEGER,
        rsBU02Bit15                             INTEGER,
        
        rsBU03ActivatedDisplayBlinking          INTEGER,
        rsBU03ActivatedDisplayOn                INTEGER,
        rsBU03ServiceDisplayBlinking            INTEGER,
        rsBU03ServiceDisplayOn                  INTEGER,
        rsBU03FailureDisplayBlinking            INTEGER,
        rsBU03FailureDisplayOn                  INTEGER,
        rsBU03OperatingDisplayBlinking          INTEGER,
        rsBU03OperatingDisplayOn                INTEGER,
        rsBU03ManualActivationDisplayBlinking   INTEGER,
        rsBU03ManualActivationDisplayOn         INTEGER,
        rsBU03OnlineDisplayDisplayOn            INTEGER,
        rsBU03IgnitionLineActivatedDisplayOn    INTEGER,
        rsBU03CutOffLineActivatedDisplayOn      INTEGER,
        rsBU03DoorSwitchDisplayOn               INTEGER,
        rsBU03Bit14                             INTEGER,
        rsBU03Bit15                             INTEGER,
        
        rsBU04ActivatedDisplayBlinking          INTEGER,
        rsBU04ActivatedDisplayOn                INTEGER,
        rsBU04ServiceDisplayBlinking            INTEGER,
        rsBU04ServiceDisplayOn                  INTEGER,
        rsBU04FailureDisplayBlinking            INTEGER,
        rsBU04FailureDisplayOn                  INTEGER,
        rsBU04OperatingDisplayBlinking          INTEGER,
        rsBU04OperatingDisplayOn                INTEGER,
        rsBU04ManualActivationDisplayBlinking   INTEGER,
        rsBU04ManualActivationDisplayOn         INTEGER,
        rsBU04OnlineDisplayDisplayOn            INTEGER,
        rsBU04IgnitionLineActivatedDisplayOn    INTEGER,
        rsBU04CutOffLineActivatedDisplayOn      INTEGER,
        rsBU04DoorSwitchDisplayOn               INTEGER,
        rsBU04Bit14                             INTEGER,
        rsBU04Bit15                             INTEGER,
        
        rsBU05ActivatedDisplayBlinking          INTEGER,
        rsBU05ActivatedDisplayOn                INTEGER,
        rsBU05ServiceDisplayBlinking            INTEGER,
        rsBU05ServiceDisplayOn                  INTEGER,
        rsBU05FailureDisplayBlinking            INTEGER,
        rsBU05FailureDisplayOn                  INTEGER,
        rsBU05OperatingDisplayBlinking          INTEGER,
        rsBU05OperatingDisplayOn                INTEGER,
        rsBU05ManualActivationDisplayBlinking   INTEGER,
        rsBU05ManualActivationDisplayOn         INTEGER,
        rsBU05OnlineDisplayDisplayOn            INTEGER,
        rsBU05IgnitionLineActivatedDisplayOn    INTEGER,
        rsBU05CutOffLineActivatedDisplayOn      INTEGER,
        rsBU05DoorSwitchDisplayOn               INTEGER,
        rsBU05Bit14                             INTEGER,
        rsBU05Bit15                             INTEGER,
        
        rsBU06ActivatedDisplayBlinking          INTEGER,
        rsBU06ActivatedDisplayOn                INTEGER,
        rsBU06ServiceDisplayBlinking            INTEGER,
        rsBU06ServiceDisplayOn                  INTEGER,
        rsBU06FailureDisplayBlinking            INTEGER,
        rsBU06FailureDisplayOn                  INTEGER,
        rsBU06OperatingDisplayBlinking          INTEGER,
        rsBU06OperatingDisplayOn                INTEGER,
        rsBU06ManualActivationDisplayBlinking   INTEGER,
        rsBU06ManualActivationDisplayOn         INTEGER,
        rsBU06OnlineDisplayDisplayOn            INTEGER,
        rsBU06IgnitionLineActivatedDisplayOn    INTEGER,
        rsBU06CutOffLineActivatedDisplayOn      INTEGER,
        rsBU06DoorSwitchDisplayOn               INTEGER,
        rsBU06Bit14                             INTEGER,
        rsBU06Bit15                             INTEGER,
        
        rsBU07ActivatedDisplayBlinking          INTEGER,
        rsBU07ActivatedDisplayOn                INTEGER,
        rsBU07ServiceDisplayBlinking            INTEGER,
        rsBU07ServiceDisplayOn                  INTEGER,
        rsBU07FailureDisplayBlinking            INTEGER,
        rsBU07FailureDisplayOn                  INTEGER,
        rsBU07OperatingDisplayBlinking          INTEGER,
        rsBU07OperatingDisplayOn                INTEGER,
        rsBU07ManualActivationDisplayBlinking   INTEGER,
        rsBU07ManualActivationDisplayOn         INTEGER,
        rsBU07OnlineDisplayDisplayOn            INTEGER,
        rsBU07IgnitionLineActivatedDisplayOn    INTEGER,
        rsBU07CutOffLineActivatedDisplayOn      INTEGER,
        rsBU07DoorSwitchDisplayOn               INTEGER,
        rsBU07Bit14                             INTEGER,
        rsBU07Bit15                             INTEGER,
        
        rsBU08ActivatedDisplayBlinking          INTEGER,
        rsBU08ActivatedDisplayOn                INTEGER,
        rsBU08ServiceDisplayBlinking            INTEGER,
        rsBU08ServiceDisplayOn                  INTEGER,
        rsBU08FailureDisplayBlinking            INTEGER,
        rsBU08FailureDisplayOn                  INTEGER,
        rsBU08OperatingDisplayBlinking          INTEGER,
        rsBU08OperatingDisplayOn                INTEGER,
        rsBU08ManualActivationDisplayBlinking   INTEGER,
        rsBU08ManualActivationDisplayOn         INTEGER,
        rsBU08OnlineDisplayDisplayOn            INTEGER,
        rsBU08IgnitionLineActivatedDisplayOn    INTEGER,
        rsBU08CutOffLineActivatedDisplayOn      INTEGER,
        rsBU08DoorSwitchDisplayOn               INTEGER,
        rsBU08Bit14                             INTEGER,
        rsBU08Bit15                             INTEGER,
        
        rsBU09ActivatedDisplayBlinking          INTEGER,
        rsBU09ActivatedDisplayOn                INTEGER,
        rsBU09ServiceDisplayBlinking            INTEGER,
        rsBU09ServiceDisplayOn                  INTEGER,
        rsBU09FailureDisplayBlinking            INTEGER,
        rsBU09FailureDisplayOn                  INTEGER,
        rsBU09OperatingDisplayBlinking          INTEGER,
        rsBU09OperatingDisplayOn                INTEGER,
        rsBU09ManualActivationDisplayBlinking   INTEGER,
        rsBU09ManualActivationDisplayOn         INTEGER,
        rsBU09OnlineDisplayDisplayOn            INTEGER,
        rsBU09IgnitionLineActivatedDisplayOn    INTEGER,
        rsBU09CutOffLineActivatedDisplayOn      INTEGER,
        rsBU09DoorSwitchDisplayOn               INTEGER,
        rsBU09Bit14                             INTEGER,
        rsBU09Bit15                             INTEGER,
        
        rsBU10ActivatedDisplayBlinking          INTEGER,
        rsBU10ActivatedDisplayOn                INTEGER,
        rsBU10ServiceDisplayBlinking            INTEGER,
        rsBU10ServiceDisplayOn                  INTEGER,
        rsBU10FailureDisplayBlinking            INTEGER,
        rsBU10FailureDisplayOn                  INTEGER,
        rsBU10OperatingDisplayBlinking          INTEGER,
        rsBU10OperatingDisplayOn                INTEGER,
        rsBU10ManualActivationDisplayBlinking   INTEGER,
        rsBU10ManualActivationDisplayOn         INTEGER,
        rsBU10OnlineDisplayDisplayOn            INTEGER,
        rsBU10IgnitionLineActivatedDisplayOn    INTEGER,
        rsBU10CutOffLineActivatedDisplayOn      INTEGER,
        rsBU10DoorSwitchDisplayOn               INTEGER,
        rsBU10Bit14                             INTEGER,
        rsBU10Bit15                             INTEGER,
        
        -- Reset control data bits
        
        rsCtrlBit00             INTEGER,
        rsCtrlBit01             INTEGER,
        rsCtrlBit02             INTEGER,
        rsCtrlBit03             INTEGER,
        rsCtrlBit04             INTEGER,
        rsBuzzerReset           INTEGER,
        rsMessageStorageReset   INTEGER,
        rsAlarmAndFailureReset  INTEGER,
        
        -- Values for temperature 1

        rsTemperature1String        OCTET STRING,
        rsTemperature1Integer       INTEGER,
        rsTemperature1IntMul100     INTEGER,

        -- Values for temperature 2

        rsTemperature2String        OCTET STRING,
        rsTemperature2Integer       INTEGER,
        rsTemperature2IntMul100     INTEGER,

        -- Values for temperature 3

        rsTemperature3String        OCTET STRING,
        rsTemperature3Integer       INTEGER,
        rsTemperature3IntMul100     INTEGER,

        -- Values for temperature 4

        rsTemperature4String        OCTET STRING,
        rsTemperature4Integer       INTEGER,
        rsTemperature4IntMul100     INTEGER,

            -- Values for temperature 5

        rsTemperature5String        OCTET STRING,
        rsTemperature5Integer       INTEGER,
        rsTemperature5IntMul100     INTEGER,

            -- Values for air temperature
            
        rsAirTemperatureString      OCTET STRING,
        rsAirTemperatureInteger     INTEGER,
        rsAirTemperatureIntMul100   INTEGER,

            -- Values for air flow speed
            
        rsAirFlowSpeedString        OCTET STRING,
        rsAirFlowSpeedInteger       INTEGER,
        rsAirFlowSpeedIntMul100     INTEGER,

            -- Values for smoke level 1

        rsSmokeLevel1String         OCTET STRING,
        rsSmokeLevel1Integer        INTEGER,
        rsSmokeLevel1IntMul100      INTEGER,

            -- Values for smoke level 2

        rsSmokeLevel2String         OCTET STRING,
        rsSmokeLevel2Integer        INTEGER,
        rsSmokeLevel2IntMul100      INTEGER,

            -- Values for detector 1 sensibility

        rsSensibility1String        OCTET STRING,
        rsSensibility1Integer       INTEGER,
        rsSensibility1IntMul100     INTEGER,

            -- Values for detector 2 sensibility

        rsSensibility2String        OCTET STRING,
        rsSensibility2Integer       INTEGER,
        rsSensibility2IntMul100     INTEGER,

            -- Values for alarm temperature 1

        rsAlarmTemp1String          OCTET STRING,
        rsAlarmTemp1Integer         INTEGER,
        rsAlarmTemp1IntMul100       INTEGER,

            -- Values for alarm temperature 2

        rsAlarmTemp2String          OCTET STRING,
        rsAlarmTemp2Integer         INTEGER,
        rsAlarmTemp2IntMul100       INTEGER,

            -- Values for alarm temperature 3

        rsAlarmTemp3String          OCTET STRING,
        rsAlarmTemp3Integer         INTEGER,
        rsAlarmTemp3IntMul100       INTEGER,

            -- Values for alarm temperature 4

        rsAlarmTemp4String          OCTET STRING,
        rsAlarmTemp4Integer         INTEGER,
        rsAlarmTemp4IntMul100       INTEGER,

            -- Values for alarm temperature 5

        rsAlarmTemp5String          OCTET STRING,
        rsAlarmTemp5Integer         INTEGER,
        rsAlarmTemp5IntMul100       INTEGER,

            -- Values for fan voltage

        rsFanVoltageString          OCTET STRING,
        rsFanVoltageInteger         INTEGER,
        rsFanVoltageIntMul100       INTEGER,

            -- Values for flow reference

        rsFlowReferenceString       OCTET STRING,
        rsFlowReferenceInteger      INTEGER,
        rsFlowReferenceIntMul100    INTEGER
    }

    ----------------------------------------------------
    -- RackSens object data description
    ----------------------------------------------------

    objectIndex OBJECT-TYPE
        SYNTAX  INTEGER (0..1)
        ACCESS  read-only
        STATUS  mandatory
        DESCRIPTION
                "A unique value for each table."
        ::= { objectEntry 99 } 

    rsUnitState OBJECT-TYPE
        SYNTAX OCTET STRING
        ACCESS read-only
        STATUS mandatory
        DESCRIPTION
            "The actual state of the RackSens. It consists of 16 bit from which every
             one of them can be examined under id 24576000 to 24676015."
        ::= { objectEntry 24576 }

    rsUnitSerialNumber          OBJECT-TYPE 
        SYNTAX INTEGER (0..999999999)
        ACCESS read-only 
        STATUS mandatory 
        DESCRIPTION 
            "The serial number of the mainboard in the RackSens."
        ::= { objectEntry 24577 }
        
    rsDetector1SerialNumber     OBJECT-TYPE 
        SYNTAX INTEGER (0..999999999)
        ACCESS read-only 
        STATUS mandatory 
        DESCRIPTION 
            "The serial number of the first detector module in the RackSens."
        ::= { objectEntry 24578 }
        
    rsDetector2SerialNumber     OBJECT-TYPE 
        SYNTAX INTEGER (0..999999999)
        ACCESS read-only 
        STATUS mandatory 
        DESCRIPTION 
            "The serial number of the second detector module in the RackSens."
        ::= { objectEntry 24579 }
        
    rsTemperature1              OBJECT-TYPE 
        SYNTAX Opaque       
        ACCESS read-only 
        STATUS mandatory 
        DESCRIPTION 
            "The temperature on sensor 1 in Celsius."
        ::= { objectEntry 24580 }
        
    rsTemperature2              OBJECT-TYPE 
        SYNTAX Opaque       
        ACCESS read-only 
        STATUS mandatory 
        DESCRIPTION 
            "The temperature on sensor 2 in Celsius."
        ::= { objectEntry 24581 }
        
    rsTemperature3              OBJECT-TYPE 
        SYNTAX Opaque       
        ACCESS read-only 
        STATUS mandatory 
        DESCRIPTION 
            "The temperature on sensor 3 in Celsius."
        ::= { objectEntry 24582 }
        
    rsTemperature4              OBJECT-TYPE 
        SYNTAX Opaque       
        ACCESS read-only 
        STATUS mandatory 
        DESCRIPTION 
            "The temperature on sensor 4 in Celsius."
        ::= { objectEntry 24583 }
        
    rsTemperature5              OBJECT-TYPE 
        SYNTAX Opaque       
        ACCESS read-only 
        STATUS mandatory 
        DESCRIPTION 
            "The temperature on sensor 5 in Celsius."
        ::= { objectEntry 24584 }
        
    rsAirTemperature            OBJECT-TYPE 
        SYNTAX Opaque       
        ACCESS read-only 
        STATUS mandatory 
        DESCRIPTION 
            "The sampled air temperature in Celsius."
        ::= { objectEntry 24585 }
        
    rsAirFlow                   OBJECT-TYPE 
        SYNTAX Opaque       
        ACCESS read-only 
        STATUS mandatory 
        DESCRIPTION 
            "The air flow speed at the unit inlet in m/s."
        ::= { objectEntry 24586 }
        
    rsAirFlowdeviation          OBJECT-TYPE 
        SYNTAX INTEGER (-32768..32767)
        ACCESS read-only 
        STATUS mandatory 
        DESCRIPTION 
            "The air flow deviation from the set point in %."
        ::= { objectEntry 24587 }
        
    rsFirePlace                 OBJECT-TYPE 
        SYNTAX INTEGER {
            samplingPointA(1),
            samplingPointB(2),
            samplingPointC(3),
            samplingPointD(4),
            samplingPointE(5),
            unknown(-1)
        }      
        ACCESS read-only 
        STATUS mandatory 
        DESCRIPTION 
            "The located fire place, where sampling pint A is the nearest hole,
            seen from the unit."
        ::= { objectEntry 24588 }
        
    rsDisplayData               OBJECT-TYPE 
        SYNTAX OCTET 
        STRING ACCESS read-only 
        STATUS mandatory 
        DESCRIPTION 
            "The actual state of the RackSens display.
             It consists of 24 bit from which every
             one of them can be examined under id 24589000 to 24689023."
        ::= { objectEntry 24589 }
        
    rsStateInfo                 OBJECT-TYPE 
        SYNTAX OCTET 
        STRING ACCESS read-only 
        STATUS mandatory 
        DESCRIPTION 
            "The complete state information of the RackSens.
             It consists of 144 bit from which every
             one of them can be examined under id 24590000 to 24690143."
        ::= { objectEntry 24590 }
        
    
    -- Smoke detector data
    
    rsMainAlarmThreshold1       OBJECT-TYPE 
        SYNTAX INTEGER (0..100)
        ACCESS read-only 
        STATUS mandatory 
        DESCRIPTION 
            "The fire alarm threshold for detector 1.
             The value is in percent from the chosen sensibility."
        ::= { objectEntry 24591 }
        
    rsPreAlarmThreshold1        OBJECT-TYPE 
        SYNTAX INTEGER (0..100)
        ACCESS read-only 
        STATUS mandatory 
        DESCRIPTION 
            "The action alarm threshold for detector 1.
             The value is in percent from the chosen sensibility."
        ::= { objectEntry 24592 }
        
    rsBargraphLevel1            OBJECT-TYPE 
        SYNTAX INTEGER (0..255)
        ACCESS read-only 
        STATUS mandatory 
        DESCRIPTION 
            "The bargraph level from detector 1.
             The value is in percent from the chosen sensibility."
        ::= { objectEntry 24593 }
        
    rsSmokeLevel1               OBJECT-TYPE 
        SYNTAX Opaque
        ACCESS read-only 
        STATUS mandatory 
        DESCRIPTION 
            "The smoke level from detector 1.
             The obscuration value is in %/m."
        ::= { objectEntry 24594 }
        
    rsChamberState1             OBJECT-TYPE 
        SYNTAX INTEGER (-32768..32767)
        ACCESS read-only 
        STATUS mandatory 
        DESCRIPTION 
            "The chamber deviation from the calibration point.
             The value is in percent from the chamber deviation limits,
             where a chamber fault condition occures."
        ::= { objectEntry 24595 }
        
    rsMainAlarmThreshold2       OBJECT-TYPE 
        SYNTAX INTEGER (0..100)
        ACCESS read-only 
        STATUS mandatory 
        DESCRIPTION 
            "The fire alarm threshold for detector 2.
             The value is in percent from the chosen sensibility."
        ::= { objectEntry 24596 }
        
    rsPreAlarmThreshold2        OBJECT-TYPE 
        SYNTAX INTEGER (0..100)
        ACCESS read-only 
        STATUS mandatory 
        DESCRIPTION 
            "The action alarm threshold for detector 2.
             The value is in percent from the chosen sensibility."
        ::= { objectEntry 24597 }
        
    rsBargraphLevel2            OBJECT-TYPE 
        SYNTAX INTEGER (0..255)
        ACCESS read-only 
        STATUS mandatory 
        DESCRIPTION 
            "The bargraph level from detector 2.
             The value is in percent from the chosen sensibility."
        ::= { objectEntry 24598 }
        
    rsSmokeLevel2               OBJECT-TYPE 
        SYNTAX Opaque       
        ACCESS read-only 
        STATUS mandatory 
        DESCRIPTION 
            "The smoke level from detector 2.
             The obscuration value is in %/m."
        ::= { objectEntry 24599 }
        
    rsChamberState2             OBJECT-TYPE 
        SYNTAX INTEGER (-32768..32767)
        ACCESS read-only 
        STATUS mandatory 
        DESCRIPTION 
            "The chamber deviation from the calibration point.
             The value is in percent from the chamber deviation limits,
             where a chamber fault condition occures."
        ::= { objectEntry 24600 }
        

    -- Adjustments
    
    rsAlarmDelayTime            OBJECT-TYPE 
        SYNTAX INTEGER (0..255)
        ACCESS read-only 
        STATUS mandatory 
        DESCRIPTION 
            "The alarm delay time in s."
        ::= { objectEntry 24601 }
        
    rsAirFlowFailureThreshold   OBJECT-TYPE 
        SYNTAX INTEGER (0..100)
        ACCESS read-only 
        STATUS mandatory 
        DESCRIPTION 
            "The flow deviation threshold,
             in percent from the air flow set point."
        ::= { objectEntry 24602 }
        
    rsAirFlowFailureDelayTime   OBJECT-TYPE 
        SYNTAX INTEGER (0..65535)
        ACCESS read-only 
        STATUS mandatory 
        DESCRIPTION 
            "The air flow failure delay time in s."
        ::= { objectEntry 24603 }
        
    rsExtinguishPreWarnTime     OBJECT-TYPE 
        SYNTAX INTEGER (0..255)
        ACCESS read-only 
        STATUS mandatory 
        DESCRIPTION 
            "The warning time in seconds,
             that are used to warn people before extinguishing."
        ::= { objectEntry 24604 }
        
    rsDetector1Sensibility      OBJECT-TYPE 
        SYNTAX Opaque       
        ACCESS read-only 
        STATUS mandatory 
        DESCRIPTION 
            "The sensibility of detector 1 in %/m."
        ::= { objectEntry 24605 }
        
    rsDetector2Sensibility      OBJECT-TYPE 
        SYNTAX Opaque       
        ACCESS read-only 
        STATUS mandatory 
        DESCRIPTION 
            "The sensibility of detector 2 in %/m."
        ::= { objectEntry 24606 }
        
    rsAlarmTemperatureSensor1   OBJECT-TYPE 
        SYNTAX Opaque       
        ACCESS read-only 
        STATUS mandatory 
        DESCRIPTION 
            "The alarm temperature of temperature sensor 1 in celsius."
        ::= { objectEntry 24607 }
        
    rsAlarmTemperatureSensor2   OBJECT-TYPE 
        SYNTAX Opaque       
        ACCESS read-only 
        STATUS mandatory 
        DESCRIPTION 
            "The alarm temperature of temperature sensor 2 in celsius."
        ::= { objectEntry 24608 }
        
    rsAlarmTemperatureSensor3   OBJECT-TYPE 
        SYNTAX Opaque       
        ACCESS read-only 
        STATUS mandatory 
        DESCRIPTION 
            "The alarm temperature of temperature sensor 3 in celsius."
        ::= { objectEntry 24609 }
        
    rsAlarmTemperatureSensor4   OBJECT-TYPE 
        SYNTAX Opaque       
        ACCESS read-only 
        STATUS mandatory 
        DESCRIPTION 
            "The alarm temperature of temperature sensor 4 in celsius."
        ::= { objectEntry 24610 }
        
    rsAlarmTemperatureSensor5   OBJECT-TYPE 
        SYNTAX Opaque       
        ACCESS read-only 
        STATUS mandatory 
        DESCRIPTION 
            "The alarm temperature of temperature sensor 5 in celsius."
        ::= { objectEntry 24611 }
        
    rsFanVoltage                OBJECT-TYPE 
        SYNTAX Opaque       
        ACCESS read-only 
        STATUS mandatory 
        DESCRIPTION 
            "The fan supply voltage in V."
        ::= { objectEntry 24612 }
        
    
    -- Bus element 1..10
    
    rsBusUnit01SerialNumber     OBJECT-TYPE 
        SYNTAX INTEGER (0..999999999)
        ACCESS read-only 
        STATUS mandatory 
        DESCRIPTION 
            "The serial number of the mainboard in the bus unit 1."
        ::= { objectEntry 24613 }
        
    rsBusUnit02SerialNumber     OBJECT-TYPE 
        SYNTAX INTEGER (0..999999999)
        ACCESS read-only 
        STATUS mandatory 
        DESCRIPTION 
            "The serial number of the mainboard in the bus unit 2."
        ::= { objectEntry 24614 }
        
    rsBusUnit03SerialNumber     OBJECT-TYPE 
        SYNTAX INTEGER (0..999999999)
        ACCESS read-only 
        STATUS mandatory 
        DESCRIPTION 
            "The serial number of the mainboard in the bus unit 3."
        ::= { objectEntry 24615 }
        
    rsBusUnit04SerialNumber     OBJECT-TYPE 
        SYNTAX INTEGER (0..999999999)
        ACCESS read-only 
        STATUS mandatory 
        DESCRIPTION 
            "The serial number of the mainboard in the bus unit 4."
        ::= { objectEntry 24616 }
        
    rsBusUnit05SerialNumber     OBJECT-TYPE 
        SYNTAX INTEGER (0..999999999)
        ACCESS read-only 
        STATUS mandatory 
        DESCRIPTION 
            "The serial number of the mainboard in the bus unit 5."
        ::= { objectEntry 24617 }
        
    rsBusUnit06SerialNumber     OBJECT-TYPE 
        SYNTAX INTEGER (0..999999999)
        ACCESS read-only 
        STATUS mandatory 
        DESCRIPTION 
            "The serial number of the mainboard in the bus unit 6."
        ::= { objectEntry 24618 }
        
    rsBusUnit07SerialNumber     OBJECT-TYPE 
        SYNTAX INTEGER (0..999999999)
        ACCESS read-only 
        STATUS mandatory 
        DESCRIPTION 
            "The serial number of the mainboard in the bus unit 7."
        ::= { objectEntry 24619 }
        
    rsBusUnit08SerialNumber     OBJECT-TYPE 
        SYNTAX INTEGER (0..999999999)
        ACCESS read-only 
        STATUS mandatory 
        DESCRIPTION 
            "The serial number of the mainboard in the bus unit 8."
        ::= { objectEntry 24620 }
        
    rsBusUnit09SerialNumber     OBJECT-TYPE 
        SYNTAX INTEGER (0..999999999)
        ACCESS read-only 
        STATUS mandatory 
        DESCRIPTION 
            "The serial number of the mainboard in the bus unit 9."
        ::= { objectEntry 24621 }
        
    rsBusUnit10SerialNumber     OBJECT-TYPE 
        SYNTAX INTEGER (0..999999999)
        ACCESS read-only 
        STATUS mandatory 
        DESCRIPTION 
            "The serial number of the mainboard in the bus unit 10."
        ::= { objectEntry 24622 }
        
    rsBusUnitStateInfo          OBJECT-TYPE 
        SYNTAX OCTET STRING 
        ACCESS read-only 
        STATUS mandatory 
        DESCRIPTION 
            "The state information bits for all bus units. 
            It consists of 200 bit from which every
             one of them can be examined under id 24623000 to 24623199."
        ::= { objectEntry 24623 }
        
    rsBusUnitDisplayData        OBJECT-TYPE 
        SYNTAX OCTET STRING 
        ACCESS read-only 
        STATUS mandatory 
        DESCRIPTION 
            "The actual state of all bus units displays. 
            It consists of 160 bit from which every
             one of them can be examined under id 24624000 to 24624159."
        ::= { objectEntry 24624 }
        
    
    -- Reset control data
    
    rsResetControl              OBJECT-TYPE 
        SYNTAX OCTET STRING 
        ACCESS read-only
        STATUS mandatory 
        DESCRIPTION 
            "The reset control bits.
             Then consists of 8 bit from which every one of them
             can be examined under id 24625000 to 24625007."
        ::= { objectEntry 24625 }
        
    -- Flow reference
    
    rsFlowReference             OBJECT-TYPE 
        SYNTAX Opaque       
        ACCESS read-only
        STATUS mandatory 
        DESCRIPTION 
            "The air flow reference value in m/s."
        ::= { objectEntry 24626 }
        


    ----------------------------------------------------
    -- Bits from RackSens data object 24576 (6000 hex)
    ----------------------------------------------------

    rsExtinguishing OBJECT-TYPE
        SYNTAX INTEGER {
            off(0),
            on(1)
        }
        ACCESS read-only
        STATUS mandatory
        DESCRIPTION
            "If one (1) the unit is extinguishing."
        ::= { objectEntry 24576000 }

    rsCutOffActive OBJECT-TYPE
        SYNTAX INTEGER {
            inactive(0),
            active(1)
        }
        ACCESS read-only
        STATUS mandatory
        DESCRIPTION
            "If one (1) the unit has engaged its cut-off relay."
        ::= { objectEntry 24576001 }

    rsManualActivation OBJECT-TYPE
        SYNTAX INTEGER {
            off(0),
            on(1)
        }
        ACCESS read-only
        STATUS mandatory
        DESCRIPTION
            "If one (1) the unit is manual activated."
        ::= { objectEntry 24576002 }

    rsMainAlarmD1 OBJECT-TYPE
        SYNTAX INTEGER {
            off(0),
            on(1)
        }
        ACCESS read-only
        STATUS mandatory
        DESCRIPTION
            "If one (1) the detector 1 is in fire alarm state."
        ::= { objectEntry 24576003 }

    rsMainAlarmD2 OBJECT-TYPE
        SYNTAX INTEGER {
            off(0),
            on(1)
        }
        ACCESS read-only
        STATUS mandatory
        DESCRIPTION
            "If one (1) the detector 2 is in fire alarm state."
        ::= { objectEntry 24576004 }

    rsPreAlarmD1 OBJECT-TYPE
        SYNTAX INTEGER {
            off(0),
            on(1)
        }
        ACCESS read-only
        STATUS mandatory
        DESCRIPTION
            "If one (1) the detector 1 is in action alarm state."
        ::= { objectEntry 24576005 }

    rsPreAlarmD2 OBJECT-TYPE
        SYNTAX INTEGER {
            off(0),
            on(1)
        }
        ACCESS read-only
        STATUS mandatory
        DESCRIPTION
            "If one (1) the detector 2 is in action alarm state."
        ::= { objectEntry 24576006 }

    rsTemperatureAlarm1 OBJECT-TYPE
        SYNTAX INTEGER {
            off(0),
            on(1)
        }
        ACCESS read-only
        STATUS mandatory
        DESCRIPTION
            "If one (1) the temperature sensor 1 is in alarm state."
        ::= { objectEntry 24576007 }

    rsTemperatureAlarm2 OBJECT-TYPE
        SYNTAX INTEGER {
            off(0),
            on(1)
        }
        ACCESS read-only
        STATUS mandatory
        DESCRIPTION
            "If one (1) the temperature sensor 2 is in alarm state."
        ::= { objectEntry 24576008 }

    rsTemperatureAlarm3 OBJECT-TYPE
        SYNTAX INTEGER {
            off(0),
            on(1)
        }
        ACCESS read-only
        STATUS mandatory
        DESCRIPTION
            "If one (1) the temperature sensor 3 is in alarm state."
        ::= { objectEntry 24576009 }

    rsTemperatureAlarm4 OBJECT-TYPE
        SYNTAX INTEGER {
            off(0),
            on(1)
        }
        ACCESS read-only
        STATUS mandatory
        DESCRIPTION
            "If one (1) the temperature sensor 4 is in alarm state."
        ::= { objectEntry 24576010 }

    rsTemperatureAlarm5 OBJECT-TYPE
        SYNTAX INTEGER {
            off(0),
            on(1)
        }
        ACCESS read-only
        STATUS mandatory
        DESCRIPTION
            "If one (1) the temperature sensor 5 is in alarm state."
        ::= { objectEntry 24576011 }

    rsFailure OBJECT-TYPE
        SYNTAX INTEGER {
            normal(0),
            failure(1)
        }
        ACCESS read-only
        STATUS mandatory
        DESCRIPTION
            "If one (1) the unit is failure state."
        ::= { objectEntry 24576012 }

    rsServiceOrBlocked OBJECT-TYPE
        SYNTAX INTEGER {
            normal(0),
            blocked(1)
        }
        ACCESS read-only
        STATUS mandatory
        DESCRIPTION
            "If one (1) the unit is service or blocked state."
        ::= { objectEntry 24576013 }

    rsDoorState OBJECT-TYPE
        SYNTAX INTEGER {
            closed(0),
            open(1)
        }
        ACCESS read-only
        STATUS mandatory
        DESCRIPTION
            "If one (1) the door of the rack is open."
        ::= { objectEntry 24576014 }

    rsAirFlowInit OBJECT-TYPE
        SYNTAX INTEGER {
            off(0),
            initializing(1)
        }
        ACCESS read-only
        STATUS mandatory
        DESCRIPTION
            "If one (1) the unit is air flow initialization state."
        ::= { objectEntry 24576015 }

    ----------------------------------------------------
    -- Bits from RackSens data object 24589 (600D hex)
    ----------------------------------------------------

    rsServiceDisplayBlinking                OBJECT-TYPE 
        SYNTAX INTEGER  { off(0),blinking(1) } 
        ACCESS read-only 
        STATUS mandatory 
        DESCRIPTION 
            "If set(1) the service / blocked display is blinking." 
        ::= { objectEntry 24589000 }
        
    rsServiceDisplayOn                      OBJECT-TYPE 
        SYNTAX INTEGER  { off(0),on(1)} 
        ACCESS read-only 
        STATUS mandatory 
        DESCRIPTION 
            "If set(1) the service / blocked display is steady on." 
        ::= { objectEntry 24589001 }
        
    rsMainsDisplayBlinking                  OBJECT-TYPE 
        SYNTAX INTEGER  { off(0),blinking(1) } 
        ACCESS read-only 
        STATUS mandatory 
        DESCRIPTION 
            "If set(1) the mains display is blinking." 
        ::= { objectEntry 24589002 }
        
    rsMainsDisplayOn                        OBJECT-TYPE 
        SYNTAX INTEGER  { off(0),on(1)} 
        ACCESS read-only 
        STATUS mandatory 
        DESCRIPTION 
            "If set(1) the mains display is steady on." 
        ::= { objectEntry 24589003 }
        
    rsBatteryDisplayBlinking                OBJECT-TYPE 
        SYNTAX INTEGER  { off(0),blinking(1) } 
        ACCESS read-only 
        STATUS mandatory 
        DESCRIPTION 
            "If set(1) the battery display is blinking." 
        ::= { objectEntry 24589004 }
        
    rsBatteryDisplayOn                      OBJECT-TYPE 
        SYNTAX INTEGER  { off(0),on(1)} 
        ACCESS read-only 
        STATUS mandatory 
        DESCRIPTION 
            "If set(1) the battery display is steady on." 
        ::= { objectEntry 24589005 }
        
    rsFailureDisplayBlinking                OBJECT-TYPE 
        SYNTAX INTEGER  { off(0),blinking(1) } 
        ACCESS read-only 
        STATUS mandatory 
        DESCRIPTION 
            "If set(1) the failure display is blinking." 
        ::= { objectEntry 24589006 }
        
    rsFailureDisplayOn                      OBJECT-TYPE 
        SYNTAX INTEGER  { off(0),on(1)} 
        ACCESS read-only 
        STATUS mandatory 
        DESCRIPTION 
            "If set(1) the failure display is steady on." 
        ::= { objectEntry 24589007 }
        
    rsManualActivationDisplayBlinking       OBJECT-TYPE 
        SYNTAX INTEGER  { off(0),blinking(1) } 
        ACCESS read-only 
        STATUS mandatory 
        DESCRIPTION 
            "If set(1) the manual activation display is blinking." 
        ::= { objectEntry 24589008 }
        
    rsManualActivationDisplayOn             OBJECT-TYPE 
        SYNTAX INTEGER  { off(0),on(1)} 
        ACCESS read-only 
        STATUS mandatory 
        DESCRIPTION 
            "If set(1) the manual activation display is steady on." 
        ::= { objectEntry 24589009 }
        
    rsAlarmDisplayBlinking                  OBJECT-TYPE 
        SYNTAX INTEGER  { off(0),blinking(1) } 
        ACCESS read-only 
        STATUS mandatory 
        DESCRIPTION 
            "If set(1) the fire alarm display is blinking." 
        ::= { objectEntry 24589010 }
        
    rsAlarmDisplayOn                        OBJECT-TYPE 
        SYNTAX INTEGER  { off(0),on(1)} 
        ACCESS read-only 
        STATUS mandatory 
        DESCRIPTION 
            "If set(1) the fire alarm display is steady on." 
        ::= { objectEntry 24589011 }
        
    rsOperatingDisplayBlinking              OBJECT-TYPE 
        SYNTAX INTEGER  { off(0),blinking(1) } 
        ACCESS read-only 
        STATUS mandatory 
        DESCRIPTION 
            "If set(1) the operating display is blinking." 
        ::= { objectEntry 24589012 }
        
    rsOperatingDisplayOn                    OBJECT-TYPE 
        SYNTAX INTEGER  { off(0),on(1)} 
        ACCESS read-only 
        STATUS mandatory 
        DESCRIPTION 
            "If set(1) the operating display is steady on." 
        ::= { objectEntry 24589013 }
        
    rsActivatedDisplayBlinking              OBJECT-TYPE 
        SYNTAX INTEGER  { off(0),blinking(1) } 
        ACCESS read-only 
        STATUS mandatory 
        DESCRIPTION 
            "If set(1) the 'activated' display is blinking." 
        ::= { objectEntry 24589014 }
        
    rsActivatedDisplayOn                    OBJECT-TYPE 
        SYNTAX INTEGER  { off(0),on(1)} 
        ACCESS read-only 
        STATUS mandatory 
        DESCRIPTION 
            "If set(1) the 'activated' display is steady on." 
        ::= { objectEntry 24589015 }
        
    rsDetector2PreAlarmDisplayBlinking      OBJECT-TYPE 
        SYNTAX INTEGER  { off(0),blinking(1) } 
        ACCESS read-only 
        STATUS mandatory 
        DESCRIPTION 
            "If set(1) the action alarm display for detector 2 is blinking." 
        ::= { objectEntry 24589016 }
        
    rsDetector2PreAlarmDisplayOn            OBJECT-TYPE 
        SYNTAX INTEGER  { off(0),on(1)} 
        ACCESS read-only 
        STATUS mandatory 
        DESCRIPTION 
            "If set(1) the action alarm display for detector 2 is steady on." 
        ::= { objectEntry 24589017 }
        
    rsDetector1PreAlarmDisplayBlinking      OBJECT-TYPE 
        SYNTAX INTEGER  { off(0),blinking(1) } 
        ACCESS read-only 
        STATUS mandatory 
        DESCRIPTION 
            "If set(1) the action alarm display for detector 1 is blinking." 
        ::= { objectEntry 24589018 }
        
    rsDetector1PreAlarmDisplayOn            OBJECT-TYPE 
        SYNTAX INTEGER  { off(0),on(1)} 
        ACCESS read-only 
        STATUS mandatory 
        DESCRIPTION 
            "If set(1) the action alarm display for detector 1 is steady on." 
        ::= { objectEntry 24589019 }
        
    rsDetector2MainAlarmDisplayBlinking     OBJECT-TYPE 
        SYNTAX INTEGER  { off(0),blinking(1) } 
        ACCESS read-only 
        STATUS mandatory 
        DESCRIPTION 
            "If set(1) the fire alarm display for detector 2 is blinking." 
        ::= { objectEntry 24589020 }
        
    rsDetector2MainAlarmDisplayOn           OBJECT-TYPE 
        SYNTAX INTEGER  { off(0),on(1)} 
        ACCESS read-only 
        STATUS mandatory 
        DESCRIPTION 
            "If set(1) the fire alarm display for detector 2 is steady on." 
        ::= { objectEntry 24589021 }
        
    rsDetector1MainAlarmDisplayBlinking     OBJECT-TYPE 
        SYNTAX INTEGER  { off(0),blinking(1) } 
        ACCESS read-only 
        STATUS mandatory 
        DESCRIPTION 
            "If set(1) the fire alarm display for detector 1 is blinking." 
        ::= { objectEntry 24589022 }
        
    rsDetector1MainAlarmDisplayOn           OBJECT-TYPE 
        SYNTAX INTEGER  { off(0),on(1)} 
        ACCESS read-only 
        STATUS mandatory 
        DESCRIPTION 
            "If set(1) the fire alarm display for detector 1 is steady on." 
        ::= { objectEntry 24589023 }
        

    ----------------------------------------------------
    -- Bits from RackSens data object 24590 (600E hex)
    ----------------------------------------------------

    rsDoorContact                           OBJECT-TYPE 
        SYNTAX INTEGER  { open(0),closed(1)} 
        ACCESS read-only 
        STATUS mandatory 
        DESCRIPTION 
            "Shows the state of the door contact." 
        ::= { objectEntry 24590000 }
        
    rsFailureRelay                          OBJECT-TYPE 
        SYNTAX INTEGER  { engaged(0), relaxed(1) } 
        ACCESS read-only 
        STATUS mandatory 
        DESCRIPTION 
            "Shows the state of the failure relay.
             If the unit is in failure state the relay is relaxed." 
        ::= { objectEntry 24590001 }
        
    rsServiceBlockedRelay                   OBJECT-TYPE 
        SYNTAX INTEGER  { relaxed(0), engaged(1) } 
        ACCESS read-only 
        STATUS mandatory 
        DESCRIPTION 
            "Shows the state of the service / blocked relay.
             If the unit is in service or blocked state the relay is engaged." 
        ::= { objectEntry 24590002 }
        
    rsActivatedRelay                        OBJECT-TYPE 
        SYNTAX INTEGER  { relaxed(0), engaged(1) } 
        ACCESS read-only 
        STATUS mandatory 
        DESCRIPTION 
            "Shows the state of the activated relay.
             If the unit is activated the relay is engaged." 
        ::= { objectEntry 24590003 }
        
    rsMainAlarm1Relay                       OBJECT-TYPE 
        SYNTAX INTEGER  { relaxed(0), engaged(1) } 
        ACCESS read-only 
        STATUS mandatory 
        DESCRIPTION 
            "Shows the state of the fire alarm relay for detector 1.
             If detector 1 is in fire alarm state the relay is engaged." 
        ::= { objectEntry 24590004 }
        
    rsMainAlarm2Relay                       OBJECT-TYPE 
        SYNTAX INTEGER  { relaxed(0), engaged(1) } 
        ACCESS read-only 
        STATUS mandatory 
        DESCRIPTION 
            "Shows the state of the fire alarm relay for detector 2.
             If detector 2 is in fire alarm state the relay is engaged." 
        ::= { objectEntry 24590005 }
        
    rsPreAlarm1Relay                        OBJECT-TYPE 
        SYNTAX INTEGER  { relaxed(0), engaged(1) } 
        ACCESS read-only 
        STATUS mandatory 
        DESCRIPTION 
            "Shows the state of the action alarm relay for detector 1.
             If detector 1 is in action alarm state the relay is engaged." 
        ::= { objectEntry 24590006 }
        
    rsPreAlarm2Relay                        OBJECT-TYPE 
        SYNTAX INTEGER  { relaxed(0), engaged(1) } 
        ACCESS read-only 
        STATUS mandatory 
        DESCRIPTION 
            "Shows the state of the action alarm relay for detector 2.
             If detector 2 is in action alarm state the relay is engaged." 
        ::= { objectEntry 24590007 }
        
    rsProgrammableRelay1                    OBJECT-TYPE 
        SYNTAX INTEGER  { relaxed(0), engaged(1) } 
        ACCESS read-only 
        STATUS mandatory 
        DESCRIPTION 
            "Shows the state of the programmable relay 1." 
        ::= { objectEntry 24590008 }
        
    rsProgrammableRelay2                    OBJECT-TYPE 
        SYNTAX INTEGER  { relaxed(0), engaged(1) } 
        ACCESS read-only 
        STATUS mandatory 
        DESCRIPTION 
            "Shows the state of the programmable relay 2." 
        ::= { objectEntry 24590009 }
        
    rsProgrammableRelay3                    OBJECT-TYPE 
        SYNTAX INTEGER  { relaxed(0), engaged(1) } 
        ACCESS read-only 
        STATUS mandatory 
        DESCRIPTION 
            "Shows the state of the programmable relay 3." 
        ::= { objectEntry 24590010 }
        
    rsProgrammableRelay4                    OBJECT-TYPE 
        SYNTAX INTEGER  { relaxed(0), engaged(1) } 
        ACCESS read-only 
        STATUS mandatory 
        DESCRIPTION 
            "Shows the state of the programmable relay 4." 
        ::= { objectEntry 24590011 }
        
    rsProgrammableRelay5                    OBJECT-TYPE 
        SYNTAX INTEGER  { relaxed(0), engaged(1) } 
        ACCESS read-only 
        STATUS mandatory 
        DESCRIPTION 
            "Shows the state of the programmable relay 5." 
        ::= { objectEntry 24590012 }
        
    rsTemperatureAlarm1State                OBJECT-TYPE 
        SYNTAX INTEGER  { off(0),on(1)} 
        ACCESS read-only 
        STATUS mandatory 
        DESCRIPTION 
            "Shows the state of the temperature alarm 1.
             If set(1) the temperature at the sensor has reached the alarm level." 
        ::= { objectEntry 24590013 }
        
    rsTemperatureAlarm2State                OBJECT-TYPE 
        SYNTAX INTEGER  { off(0),on(1)} 
        ACCESS read-only 
        STATUS mandatory 
        DESCRIPTION 
            "Shows the state of the temperature alarm 2.
             If set(1) the temperature at the sensor has reached the alarm level." 
        ::= { objectEntry 24590014 }
        
    rsTemperatureAlarm3State                OBJECT-TYPE 
        SYNTAX INTEGER  { off(0),on(1)} 
        ACCESS read-only 
        STATUS mandatory 
        DESCRIPTION 
            "Shows the state of the temperature alarm 3.
             If set(1) the temperature at the sensor has reached the alarm level." 
        ::= { objectEntry 24590015 }
        
    rsTemperatureAlarm4State                OBJECT-TYPE 
        SYNTAX INTEGER  { off(0),on(1)} 
        ACCESS read-only 
        STATUS mandatory 
        DESCRIPTION 
            "Shows the state of the temperature alarm 4.
             If set(1) the temperature at the sensor has reached the alarm level." 
        ::= { objectEntry 24590016 }
        
    rsTemperatureAlarm5State                OBJECT-TYPE 
        SYNTAX INTEGER  { off(0),on(1)} 
        ACCESS read-only 
        STATUS mandatory 
        DESCRIPTION 
            "Shows the state of the temperature alarm 5.
             If set(1) the temperature at the sensor has reached the alarm level." 
        ::= { objectEntry 24590017 }
        
    rsBuzzerState                           OBJECT-TYPE 
        SYNTAX INTEGER  { off(0),on(1)} 
        ACCESS read-only 
        STATUS mandatory 
        DESCRIPTION 
            "Shows the state of the buzzer." 
        ::= { objectEntry 24590018 }
        
    rsFailureStorage                        OBJECT-TYPE 
        SYNTAX INTEGER  { off(0),on(1)} 
        ACCESS read-only 
        STATUS mandatory 
        DESCRIPTION 
            "Shows the state of the failure storage flag.
             If set(1) the failure display remains on even if the failure disappeared." 
        ::= { objectEntry 24590019 }
        
    rsDynamicAirFlowControl                 OBJECT-TYPE 
        SYNTAX INTEGER  { off(0),on(1)} 
        ACCESS read-only 
        STATUS mandatory 
        DESCRIPTION 
            "Shows the state of the dynamic air flow control flag.
             If set(1) the air flow rate is also controlled for small fast deviations,
             which are initiated when sampling holes are closed." 
        ::= { objectEntry 24590020 }
        
    rsAirFlowInitState                      OBJECT-TYPE 
        SYNTAX INTEGER  { off(0),on(1)} 
        ACCESS read-only 
        STATUS mandatory 
        DESCRIPTION 
            "This flag is on(1) during the air flow initialization procedure." 
        ::= { objectEntry 24590021 }
        
    rsRoomIdentState                        OBJECT-TYPE 
        SYNTAX INTEGER  { off(0),on(1)} 
        ACCESS read-only 
        STATUS mandatory 
        DESCRIPTION 
            "This flag is on(1) when the room identification function is switched on." 
        ::= { objectEntry 24590022 }
        
    rsMainAlarmAfterRoomIdent               OBJECT-TYPE 
        SYNTAX INTEGER  { off(0),on(1)} 
        ACCESS read-only 
        STATUS mandatory 
        DESCRIPTION 
            "If this flag is on(1), then the fire alarm is delayed
             until the room identification has terminated." 
        ::= { objectEntry 24590023 }
        
    rsLogicSensDetector1State               OBJECT-TYPE 
        SYNTAX INTEGER  { off(0),on(1)} 
        ACCESS read-only 
        STATUS mandatory 
        DESCRIPTION 
            "This flag is on(1) when the 'LogicSens' function
             for detector 1 is switched on." 
        ::= { objectEntry 24590024 }
        
    rsLogicSensDetector2State               OBJECT-TYPE 
        SYNTAX INTEGER  { off(0),on(1)} 
        ACCESS read-only 
        STATUS mandatory 
        DESCRIPTION 
            "This flag is on(1) when the 'LogicSens' function
             for detector 2 is switched on." 
        ::= { objectEntry 24590025 }
        
    rsDetectorBox2Registrated               OBJECT-TYPE 
        SYNTAX INTEGER  { no(0),yes(1) } 
        ACCESS read-only 
        STATUS mandatory 
        DESCRIPTION 
            "This flag is set(1) when the second detector has been connected." 
        ::= { objectEntry 24590026 }
        
    rsBusUnit1Registrated                   OBJECT-TYPE 
        SYNTAX INTEGER  { no(0),yes(1) } 
        ACCESS read-only 
        STATUS mandatory 
        DESCRIPTION 
            "This flag is set(1) when the first bus unit has been connected." 
        ::= { objectEntry 24590027 }
        
    rsBusUnit2Registrated                   OBJECT-TYPE 
        SYNTAX INTEGER  { no(0),yes(1) } 
        ACCESS read-only 
        STATUS mandatory 
        DESCRIPTION 
            "This flag is set(1) when the second bus unit has been connected." 
        ::= { objectEntry 24590028 }
        
    rsBusUnit3Registrated                   OBJECT-TYPE 
        SYNTAX INTEGER  { no(0),yes(1) } 
        ACCESS read-only 
        STATUS mandatory 
        DESCRIPTION 
            "This flag is set(1) when the third bus unit has been connected." 
        ::= { objectEntry 24590029 }
        
    rsBusUnit4Registrated                   OBJECT-TYPE 
        SYNTAX INTEGER  { no(0),yes(1) } 
        ACCESS read-only 
        STATUS mandatory 
        DESCRIPTION 
            "This flag is set(1) when the fourth bus unit has been connected." 
        ::= { objectEntry 24590030 }
        
    rsBusUnit5Registrated                   OBJECT-TYPE 
        SYNTAX INTEGER  { no(0),yes(1) } 
        ACCESS read-only 
        STATUS mandatory 
        DESCRIPTION 
            "This flag is set(1) when the fifth bus unit has been connected." 
        ::= { objectEntry 24590031 }
        
    rsBusUnit6Registrated                   OBJECT-TYPE 
        SYNTAX INTEGER  { no(0),yes(1) } 
        ACCESS read-only 
        STATUS mandatory 
        DESCRIPTION 
            "This flag is set(1) when the sixt bus unit has been connected." 
        ::= { objectEntry 24590032 }
        
    rsBusUnit7Registrated                   OBJECT-TYPE 
        SYNTAX INTEGER  { no(0),yes(1) } 
        ACCESS read-only 
        STATUS mandatory 
        DESCRIPTION 
            "This flag is set(1) when the seventh bus unit has been connected." 
        ::= { objectEntry 24590033 }
        
    rsBusUnit8Registrated                   OBJECT-TYPE 
        SYNTAX INTEGER  { no(0),yes(1) } 
        ACCESS read-only 
        STATUS mandatory 
        DESCRIPTION 
            "This flag is set(1) when the eighth bus unit has been connected." 
        ::= { objectEntry 24590034 }
        
    rsBusUnit9Registrated                   OBJECT-TYPE 
        SYNTAX INTEGER  { no(0),yes(1) } 
        ACCESS read-only 
        STATUS mandatory 
        DESCRIPTION 
            "This flag is set(1) when the nineth bus unit has been connected." 
        ::= { objectEntry 24590035 }
        
    rsBusUnit10Registrated                  OBJECT-TYPE 
        SYNTAX INTEGER  { no(0),yes(1) } 
        ACCESS read-only 
        STATUS mandatory 
        DESCRIPTION 
            "This flag is set(1) when the tenth bus unit has been connected." 
        ::= { objectEntry 24590036 }
        
    rsTempSensor1Registrated                OBJECT-TYPE 
        SYNTAX INTEGER  { no(0),yes(1) } 
        ACCESS read-only 
        STATUS mandatory 
        DESCRIPTION 
            "This flag is set(1) when the first temperature sensor has been connected." 
        ::= { objectEntry 24590037 }
        
    rsTempSensor2Registrated                OBJECT-TYPE 
        SYNTAX INTEGER  { no(0),yes(1) } 
        ACCESS read-only 
        STATUS mandatory 
        DESCRIPTION 
            "This flag is set(1) when the second temperature sensor has been connected." 
        ::= { objectEntry 24590038 }
        
    rsTempSensor3Registrated                OBJECT-TYPE 
        SYNTAX INTEGER  { no(0),yes(1) } 
        ACCESS read-only 
        STATUS mandatory 
        DESCRIPTION 
            "This flag is set(1) when the third temperature sensor has been connected." 
        ::= { objectEntry 24590039 }
        
    rsTempSensor4Registrated                OBJECT-TYPE 
        SYNTAX INTEGER  { no(0),yes(1) } 
        ACCESS read-only 
        STATUS mandatory 
        DESCRIPTION 
            "This flag is set(1) when the fourth temperature sensor has been connected." 
        ::= { objectEntry 24590040 }
        
    rsTempSensor5Registrated                OBJECT-TYPE 
        SYNTAX INTEGER  { no(0),yes(1) } 
        ACCESS read-only 
        STATUS mandatory 
        DESCRIPTION 
            "This flag is set(1) when the fifth temperature sensor has been connected." 
        ::= { objectEntry 24590041 }
        
    rsAirFlowControlAvailable               OBJECT-TYPE 
        SYNTAX INTEGER  { no(0),yes(1) } 
        ACCESS read-only 
        STATUS mandatory 
        DESCRIPTION 
            "This flag is set(1) when the air flow control logic is available." 
        ::= { objectEntry 24590042 }
        
    rsDynFlowControlAvailable               OBJECT-TYPE 
        SYNTAX INTEGER  { no(0),yes(1) } 
        ACCESS read-only 
        STATUS mandatory 
        DESCRIPTION 
            "This flag is set(1) when the dynamic air flow control logic is available." 
        ::= { objectEntry 24590043 }
        
    rsBatteryLoaderAvailable                OBJECT-TYPE 
        SYNTAX INTEGER  { no(0),yes(1) } 
        ACCESS read-only 
        STATUS mandatory 
        DESCRIPTION 
            "This flag is set(1) when the unit has a battery loader." 
        ::= { objectEntry 24590044 }
        
    rsPreAlarmDisplayAvailable              OBJECT-TYPE 
        SYNTAX INTEGER  { no(0),yes(1) } 
        ACCESS read-only 
        STATUS mandatory 
        DESCRIPTION 
            "This flag is set(1) when the unit has a action alarm display." 
        ::= { objectEntry 24590045 }
        
    rsBargraphAvailable                     OBJECT-TYPE 
        SYNTAX INTEGER  { no(0),yes(1) } 
        ACCESS read-only 
        STATUS mandatory 
        DESCRIPTION 
            "This flag is set(1) when the unit has a bargraph display." 
        ::= { objectEntry 24590046 }
        
    rsRoomIdentAvailable                    OBJECT-TYPE 
        SYNTAX INTEGER  { no(0),yes(1) } 
        ACCESS read-only 
        STATUS mandatory 
        DESCRIPTION 
            "This flag is set(1) when the room ident function is available." 
        ::= { objectEntry 24590047 }
        
    rsLogicSensDet1Available                OBJECT-TYPE 
        SYNTAX INTEGER  { no(0),yes(1) } 
        ACCESS read-only 
        STATUS mandatory 
        DESCRIPTION 
            "This flag is set(1) when the 'LogicSens' function
             in detector 1 is available." 
        ::= { objectEntry 24590048 }
        
    rsLogicSensDet2Available                OBJECT-TYPE 
        SYNTAX INTEGER  { no(0),yes(1) } 
        ACCESS read-only 
        STATUS mandatory 
        DESCRIPTION 
            "This flag is set(1) when the 'LogicSens' function
             in detector 2 is available." 
        ::= { objectEntry 24590049 }
        
    rsTempSensorsAvailable                  OBJECT-TYPE 
        SYNTAX INTEGER  { no(0),yes(1) } 
        ACCESS read-only 
        STATUS mandatory 
        DESCRIPTION 
            "This flag is set(1) when the unit can handle temperature sensors." 
        ::= { objectEntry 24590050 }
        
    rsProgRelaysAvailable                   OBJECT-TYPE 
        SYNTAX INTEGER  { no(0),yes(1) } 
        ACCESS read-only 
        STATUS mandatory 
        DESCRIPTION 
            "This flag is set(1) when the unit has programmable relays." 
        ::= { objectEntry 24590051 }
        
    rsUnitBlocked                           OBJECT-TYPE 
        SYNTAX INTEGER  { off(0),blocked(1)} 
        ACCESS read-only 
        STATUS mandatory 
        DESCRIPTION 
            "If this flag is set(1) the outputs of the unit are blocked. 
             In blocked mode all ignition circuits in the extinguishing modules are blocked." 
        ::= { objectEntry 24590052 }
        
    rsUnitIsolated                          OBJECT-TYPE 
        SYNTAX INTEGER  { normal(0),isolated(1)} 
        ACCESS read-only 
        STATUS mandatory 
        DESCRIPTION 
            "If this flag is set(1) the unit is isolated (in service mode).
             In service mode (isolated) all alarm relays remains switched off,
             all cut-off relays remains switched off,
             all programmed relays remains switched off,
             and all ignition circuits in the extinguishing modules are blocked.
             Because all display functions remains unaffected from the isolation,
             this mode is intended to check the functionality of the unit during service." 
        ::= { objectEntry 24590053 }
        
    rsSupplyVoltageLow                      OBJECT-TYPE 
        SYNTAX INTEGER  { normal(0),low(1) } 
        ACCESS read-only 
        STATUS mandatory 
        DESCRIPTION 
            "This flag is set(1) when the supply voltage of the unit is low." 
        ::= { objectEntry 24590054 }
        
    rsProgramFailure                        OBJECT-TYPE 
        SYNTAX INTEGER  { normal(0),failure(1) } 
        ACCESS read-only 
        STATUS mandatory 
        DESCRIPTION 
            "This flag is set(1) when a program or memory failure is detected." 
        ::= { objectEntry 24590055 }
        
    rsFanControlFailure                     OBJECT-TYPE 
        SYNTAX INTEGER  { normal(0),failure(1) } 
        ACCESS read-only 
        STATUS mandatory 
        DESCRIPTION 
            "This flag is set(1) when the adjusted fan voltage can't be reached." 
        ::= { objectEntry 24590056 }
        
    rsTempSensorFailure                     OBJECT-TYPE 
        SYNTAX INTEGER  { normal(0),failure(1) } 
        ACCESS read-only 
        STATUS mandatory 
        DESCRIPTION 
            "This flag is set(1) when one of the temperature sensors
             is outside it's allowed resistor range due to line shorts or broken lines." 
        ::= { objectEntry 24590057 }
        
    rsBatteryFailure                        OBJECT-TYPE 
        SYNTAX INTEGER  { normal(0),failure(1) } 
        ACCESS read-only 
        STATUS mandatory 
        DESCRIPTION 
            "This flag is set(1) when the battery survey function
             detects a battery with too high internal resistance
             or with too low capacity." 
        ::= { objectEntry 24590058 }
        
    rsMainsSupplyFailure                    OBJECT-TYPE 
        SYNTAX INTEGER  { normal(0),failure(1) } 
        ACCESS read-only 
        STATUS mandatory 
        DESCRIPTION 
            "This flag is set(1) when the mains supply control
             recognizes a undervoltage condition." 
        ::= { objectEntry 24590059 }
        
    rsManualActLineFailure                  OBJECT-TYPE 
        SYNTAX INTEGER  { normal(0),failure(1) } 
        ACCESS read-only 
        STATUS mandatory 
        DESCRIPTION 
            "This flag is set(1) when the resistor of the line
             is outside it's allowed range due to line shorts or broken lines." 
        ::= { objectEntry 24590060 }
        
    rsTooManyBusUnits                       OBJECT-TYPE 
        SYNTAX INTEGER  { off(0),on(1)} 
        ACCESS read-only 
        STATUS mandatory 
        DESCRIPTION 
            "This flag is set(1) when too many external units are connected." 
        ::= { objectEntry 24590061 }
        
    rsBusUnitFailure                        OBJECT-TYPE 
        SYNTAX INTEGER  { normal(0),failure(1) } 
        ACCESS read-only 
        STATUS mandatory 
        DESCRIPTION 
            "This flag is set(1) when one of the units, that
             are connected to the bus, is in failure state." 
        ::= { objectEntry 24590062 }
        
    rsAgentLoss                             OBJECT-TYPE 
        SYNTAX INTEGER  { normal(0),loss(1) } 
        ACCESS read-only 
        STATUS mandatory 
        DESCRIPTION 
            "This flag is set(1) when the pressure sensor detects agent loss." 
        ::= { objectEntry 24590063 }
        
    rsBusFailure                            OBJECT-TYPE 
        SYNTAX INTEGER  { normal(0),failure(1) } 
        ACCESS read-only 
        STATUS mandatory 
        DESCRIPTION 
            "This flag is set(1) when the bus to the external units
             is disturbed, shorted or broken." 
        ::= { objectEntry 24590064 }
        
    rsNetworkFailure                        OBJECT-TYPE 
        SYNTAX INTEGER  { normal(0),failure(1) } 
        ACCESS read-only 
        STATUS mandatory 
        DESCRIPTION 
            "This flag is set(1) when the unit detects a failure
             on the network card connection." 
        ::= { objectEntry 24590065 }
        
    rsDetector1CommunicationFailure         OBJECT-TYPE 
        SYNTAX INTEGER  { normal(0),failure(1) } 
        ACCESS read-only 
        STATUS mandatory 
        DESCRIPTION 
            "This flag is set(1) when the connection to detector 1
             is disturbed, shorted or broken." 
        ::= { objectEntry 24590066 }
        
    rsDetector1Failure                      OBJECT-TYPE 
        SYNTAX INTEGER  { normal(0),failure(1) } 
        ACCESS read-only 
        STATUS mandatory 
        DESCRIPTION 
            "This flag is set(1) when the detector 1 is in failure state." 
        ::= { objectEntry 24590067 }
        
    rsChamber1Dirty                         OBJECT-TYPE 
        SYNTAX INTEGER  { normal(0),dirty(1) } 
        ACCESS read-only 
        STATUS mandatory 
        DESCRIPTION 
            "This flag is set(1) when the chamber of detector 1 is dirty." 
        ::= { objectEntry 24590068 }
        
    rsAirFlowControlFailure                 OBJECT-TYPE 
        SYNTAX INTEGER  { normal(0),failure(1) } 
        ACCESS read-only 
        STATUS mandatory 
        DESCRIPTION 
            "This flag is set(1) when the air flow control logic in detector 1
             has detected a failure condition." 
        ::= { objectEntry 24590069 }
        
    rsStaticAirFlowLow                      OBJECT-TYPE 
        SYNTAX INTEGER  { normal(0),low(1) } 
        ACCESS read-only 
        STATUS mandatory 
        DESCRIPTION 
            "This flag is set(1) when the air flow rate gets too low.
             It can be caused by engorged sampling holes in the pipe." 
        ::= { objectEntry 24590070 }
        
    rsStaticAirFlowHigh                     OBJECT-TYPE 
        SYNTAX INTEGER  { normal(0),high(1) } 
        ACCESS read-only 
        STATUS mandatory 
        DESCRIPTION 
            "This flag is set(1) when the air flow rate gets too high.
             It can be caused by fissures in the pipe." 
        ::= { objectEntry 24590071 }
        
    rsDynamicAirFlowLow                     OBJECT-TYPE 
        SYNTAX INTEGER  { normal(0),low(1) } 
        ACCESS read-only 
        STATUS mandatory 
        DESCRIPTION 
            "This flag is set(1) when the dynamic air flow rate
             control detects a covered sampling hole in the pipe." 
        ::= { objectEntry 24590072 }
        
    rsDynamicAirFlowHigh                    OBJECT-TYPE 
        SYNTAX INTEGER  { normal(0),high(1) } 
        ACCESS read-only 
        STATUS mandatory 
        DESCRIPTION 
            "This flag is set(1) when the dynamic air flow rate
             control detects an enlarged sampling hole in the pipe." 
        ::= { objectEntry 24590073 }
        
    rsAirFlowInitAborted                    OBJECT-TYPE 
        SYNTAX INTEGER  { normal(0),aborted(1) } 
        ACCESS read-only 
        STATUS mandatory 
        DESCRIPTION 
            "This flag is set(1) when the air flow initialization process is aborted." 
        ::= { objectEntry 24590074 }
        
    rsRoomIdentFailure                      OBJECT-TYPE 
        SYNTAX INTEGER  { normal(0),failure(1) } 
        ACCESS read-only 
        STATUS mandatory 
        DESCRIPTION 
            "This flag is set(1) when the room identification process
             could not determine the number of the sampling hole, 
             where the smoke comes from." 
        ::= { objectEntry 24590075 }
        
    rsDetector2CommunicationFailure         OBJECT-TYPE 
        SYNTAX INTEGER  { normal(0),failure(1) } 
        ACCESS read-only 
        STATUS mandatory 
        DESCRIPTION 
            "This flag is set(1) when the connection to detector 2
             is disturbed, shorted or broken." 
        ::= { objectEntry 24590076 }
        
    rsDetector2Failure                      OBJECT-TYPE 
        SYNTAX INTEGER  { normal(0),failure(1) } 
        ACCESS read-only 
        STATUS mandatory 
        DESCRIPTION 
            "This flag is set(1) when the detector 2 is in failure state." 
        ::= { objectEntry 24590077 }
        
    rsChamber2Dirty                         OBJECT-TYPE 
        SYNTAX INTEGER  { normal(0),dirty(1) } 
        ACCESS read-only 
        STATUS mandatory 
        DESCRIPTION 
            "This flag is set(1) when the chamber of detector 2 is dirty." 
        ::= { objectEntry 24590078 }
        
    rsUnitBlockedStored                     OBJECT-TYPE 
        SYNTAX INTEGER  { off(0),stored(1) } 
        ACCESS read-only 
        STATUS mandatory 
        DESCRIPTION 
            "Stored flag: Unit blocked." 
        ::= { objectEntry 24590079 }
        
    rsUnitIsolatedStored                    OBJECT-TYPE 
        SYNTAX INTEGER  { off(0),stored(1) } 
        ACCESS read-only 
        STATUS mandatory 
        DESCRIPTION 
            "Stored flag: Unit isolated (in service mode)." 
        ::= { objectEntry 24590080 }
        
    rsSupplyVoltageLowStored                OBJECT-TYPE 
        SYNTAX INTEGER  { off(0),stored(1) } 
        ACCESS read-only 
        STATUS mandatory 
        DESCRIPTION 
            "Stored flag: Supply voltage low." 
        ::= { objectEntry 24590081 }
        
    rsProgramFailureStored                  OBJECT-TYPE 
        SYNTAX INTEGER  { off(0),stored(1) } 
        ACCESS read-only 
        STATUS mandatory 
        DESCRIPTION 
            "Stored flag: Program failure." 
        ::= { objectEntry 24590082 }
        
    rsFanControlFailureStored               OBJECT-TYPE 
        SYNTAX INTEGER  { off(0),stored(1) } 
        ACCESS read-only 
        STATUS mandatory 
        DESCRIPTION 
            "Stored flag: Fan control failure." 
        ::= { objectEntry 24590083 }
        
    rsTempSensorFailureStored               OBJECT-TYPE 
        SYNTAX INTEGER  { off(0),stored(1) } 
        ACCESS read-only 
        STATUS mandatory 
        DESCRIPTION 
            "Stored flag: Temperature sensor failure." 
        ::= { objectEntry 24590084 }
        
    rsBatteryFailureStored                  OBJECT-TYPE 
        SYNTAX INTEGER  { off(0),stored(1) } 
        ACCESS read-only 
        STATUS mandatory 
        DESCRIPTION 
            "Stored flag: Battery failure." 
        ::= { objectEntry 24590085 }
        
    rsMainsSupplyFailureStored              OBJECT-TYPE 
        SYNTAX INTEGER  { off(0),stored(1) } 
        ACCESS read-only 
        STATUS mandatory 
        DESCRIPTION 
            "Stored flag: Mains supply failure." 
        ::= { objectEntry 24590086 }
        
    rsManualActLineFailureStored            OBJECT-TYPE 
        SYNTAX INTEGER  { off(0),stored(1) } 
        ACCESS read-only 
        STATUS mandatory 
        DESCRIPTION 
            "Stored flag: Manual activation line failure." 
        ::= { objectEntry 24590087 }
        
    rsTooManyBusUnitsStored                 OBJECT-TYPE 
        SYNTAX INTEGER  { off(0),stored(1) } 
        ACCESS read-only 
        STATUS mandatory 
        DESCRIPTION 
            "Stored flag: Too many bus units." 
        ::= { objectEntry 24590088 }
        
    rsBusUnitFailureStored                  OBJECT-TYPE 
        SYNTAX INTEGER  { off(0),stored(1) } 
        ACCESS read-only 
        STATUS mandatory 
        DESCRIPTION 
            "Stored flag: Bus unit failure." 
        ::= { objectEntry 24590089 }
        
    rsAgentLossStored                       OBJECT-TYPE 
        SYNTAX INTEGER  { off(0),stored(1) } 
        ACCESS read-only 
        STATUS mandatory 
        DESCRIPTION 
            "Stored flag: Agent loss." 
        ::= { objectEntry 24590090 }
        
    rsBusFailureStored                      OBJECT-TYPE 
        SYNTAX INTEGER  { off(0),stored(1) } 
        ACCESS read-only 
        STATUS mandatory 
        DESCRIPTION 
            "Stored flag: Bus failure." 
        ::= { objectEntry 24590091 }
        
    rsNetworkFailureStored                  OBJECT-TYPE 
        SYNTAX INTEGER  { off(0),stored(1) } 
        ACCESS read-only 
        STATUS mandatory 
        DESCRIPTION 
            "Stored flag: Network failure." 
        ::= { objectEntry 24590092 }
        
    rsDetector1CommunicationFailureStored   OBJECT-TYPE 
        SYNTAX INTEGER  { off(0),stored(1) } 
        ACCESS read-only 
        STATUS mandatory 
        DESCRIPTION 
            "Stored flag: Detector 1 communication failure." 
        ::= { objectEntry 24590093 }
        
    rsDetector1FailureStored                OBJECT-TYPE 
        SYNTAX INTEGER  { off(0),stored(1) } 
        ACCESS read-only 
        STATUS mandatory 
        DESCRIPTION 
            "Stored flag: Detector 1 failure." 
        ::= { objectEntry 24590094 }
        
    rsChamber1DirtyStored                   OBJECT-TYPE 
        SYNTAX INTEGER  { off(0),stored(1) } 
        ACCESS read-only 
        STATUS mandatory 
        DESCRIPTION 
            "Stored flag: Detector 1 chamber dirty." 
        ::= { objectEntry 24590095 }
        
    rsAirFlowControlFailureStored           OBJECT-TYPE 
        SYNTAX INTEGER  { off(0),stored(1) } 
        ACCESS read-only 
        STATUS mandatory 
        DESCRIPTION 
            "Stored flag: Air flow control failure." 
        ::= { objectEntry 24590096 }
        
    rsStaticAirFlowLowStored                OBJECT-TYPE 
        SYNTAX INTEGER  { off(0),stored(1) } 
        ACCESS read-only 
        STATUS mandatory 
        DESCRIPTION 
            "Stored flag: Static air flow rate low." 
        ::= { objectEntry 24590097 }
        
    rsStaticAirFlowHighStored               OBJECT-TYPE 
        SYNTAX INTEGER  { off(0),stored(1) } 
        ACCESS read-only 
        STATUS mandatory 
        DESCRIPTION 
            "Stored flag: Static air flow rate high." 
        ::= { objectEntry 24590098 }
        
    rsDynamicAirFlowLowStored               OBJECT-TYPE 
        SYNTAX INTEGER  { off(0),stored(1) } 
        ACCESS read-only 
        STATUS mandatory 
        DESCRIPTION 
            "Stored flag: Dynamic air flow rate low." 
        ::= { objectEntry 24590099 }
        
    rsDynamicAirFlowHighStored              OBJECT-TYPE 
        SYNTAX INTEGER  { off(0),stored(1) } 
        ACCESS read-only 
        STATUS mandatory 
        DESCRIPTION 
            "Stored flag: Dynamic air flow rate high." 
        ::= { objectEntry 24590100 }
        
    rsAirFlowInitAbortedStored              OBJECT-TYPE 
        SYNTAX INTEGER  { off(0),stored(1) } 
        ACCESS read-only 
        STATUS mandatory 
        DESCRIPTION 
            "Stored flag: Air flow initialization aborted." 
        ::= { objectEntry 24590101 }
        
    rsRoomIdentFailureStored                OBJECT-TYPE 
        SYNTAX INTEGER  { off(0),stored(1) } 
        ACCESS read-only 
        STATUS mandatory 
        DESCRIPTION 
            "Stored flag: Room identification failure." 
        ::= { objectEntry 24590102 }
        
    rsDetector2CommunicationFailureStored   OBJECT-TYPE 
        SYNTAX INTEGER  { off(0),stored(1) } 
        ACCESS read-only 
        STATUS mandatory 
        DESCRIPTION 
            "Stored flag: Detector 2 communication failure." 
        ::= { objectEntry 24590103 }
        
    rsDetector2FailureStored                OBJECT-TYPE 
        SYNTAX INTEGER  { off(0),stored(1) } 
        ACCESS read-only 
        STATUS mandatory 
        DESCRIPTION 
            "Stored flag: Detector 2 failure." 
        ::= { objectEntry 24590104 }
        
    rsChamber2DirtyStored                   OBJECT-TYPE 
        SYNTAX INTEGER  { off(0),stored(1) } 
        ACCESS read-only 
        STATUS mandatory 
        DESCRIPTION 
            "Stored flag: Detector 2 chamber dirty." 
        ::= { objectEntry 24590105 }
        
    rsUnitBlockedValid                      OBJECT-TYPE 
        SYNTAX INTEGER  { invalid(0),valid(1) } 
        ACCESS read-only 
        STATUS mandatory 
        DESCRIPTION 
            "Flag: 'Unit blocked' valid if set(1)." 
        ::= { objectEntry 24590106 }
        
    rsUnitIsolatedValid                     OBJECT-TYPE 
        SYNTAX INTEGER  { invalid(0),valid(1) } 
        ACCESS read-only 
        STATUS mandatory 
        DESCRIPTION 
            "Flag: 'Unit isolated (in service mode)' valid if set(1)." 
        ::= { objectEntry 24590107 }
        
    rsSupplyVoltageLowValid                 OBJECT-TYPE 
        SYNTAX INTEGER  { invalid(0),valid(1) } 
        ACCESS read-only 
        STATUS mandatory 
        DESCRIPTION 
            "Flag: 'Supply voltage low' valid if set(1)." 
        ::= { objectEntry 24590108 }
        
    rsProgramFailureValid                   OBJECT-TYPE 
        SYNTAX INTEGER  { invalid(0),valid(1) } 
        ACCESS read-only 
        STATUS mandatory 
        DESCRIPTION 
            "Flag: 'Program failure' valid if set(1)." 
        ::= { objectEntry 24590109 }
        
    rsFanControlFailureValid                OBJECT-TYPE 
        SYNTAX INTEGER  { invalid(0),valid(1) } 
        ACCESS read-only 
        STATUS mandatory 
        DESCRIPTION 
            "Flag: 'Fan control failure' valid if set(1)." 
        ::= { objectEntry 24590110 }
        
    rsTempSensorFailureValid                OBJECT-TYPE 
        SYNTAX INTEGER  { invalid(0),valid(1) } 
        ACCESS read-only 
        STATUS mandatory 
        DESCRIPTION 
            "Flag: 'Temperature sensor failure' valid if set(1)." 
        ::= { objectEntry 24590111 }
        
    rsBatteryFailureValid                   OBJECT-TYPE 
        SYNTAX INTEGER  { invalid(0),valid(1) } 
        ACCESS read-only 
        STATUS mandatory 
        DESCRIPTION 
            "Flag: 'Battery failure' valid if set(1)." 
        ::= { objectEntry 24590112 }
        
    rsMainsSupplyFailureValid               OBJECT-TYPE 
        SYNTAX INTEGER  { invalid(0),valid(1) } 
        ACCESS read-only 
        STATUS mandatory 
        DESCRIPTION 
            "Flag: 'Mains supply failure' valid if set(1)." 
        ::= { objectEntry 24590113 }
        
    rsManualActLineFailureValid             OBJECT-TYPE 
        SYNTAX INTEGER  { invalid(0),valid(1) } 
        ACCESS read-only 
        STATUS mandatory 
        DESCRIPTION 
            "Flag: 'Manual activation line failure' valid if set(1)." 
        ::= { objectEntry 24590114 }
        
    rsTooManyBusUnitsValid                  OBJECT-TYPE 
        SYNTAX INTEGER  { invalid(0),valid(1) } 
        ACCESS read-only 
        STATUS mandatory 
        DESCRIPTION 
            "Flag: 'Too many bus units' valid if set(1)." 
        ::= { objectEntry 24590115 }
        
    rsBusUnitFailureValid                   OBJECT-TYPE 
        SYNTAX INTEGER  { invalid(0),valid(1) } 
        ACCESS read-only 
        STATUS mandatory 
        DESCRIPTION 
            "Flag: 'Bus unit failure' valid if set(1)." 
        ::= { objectEntry 24590116 }
        
    rsAgentLossValid                        OBJECT-TYPE 
        SYNTAX INTEGER  { invalid(0),valid(1) } 
        ACCESS read-only 
        STATUS mandatory 
        DESCRIPTION 
            "Flag: 'Agent loss' valid if set(1)." 
        ::= { objectEntry 24590117 }
        
    rsBusFailureValid                       OBJECT-TYPE 
        SYNTAX INTEGER  { invalid(0),valid(1) } 
        ACCESS read-only 
        STATUS mandatory 
        DESCRIPTION 
            "Flag: 'Bus failure' valid if set(1)." 
        ::= { objectEntry 24590118 }
        
    rsNetworkFailureValid                   OBJECT-TYPE 
        SYNTAX INTEGER  { invalid(0),valid(1) } 
        ACCESS read-only 
        STATUS mandatory 
        DESCRIPTION 
            "Flag: 'Network failure' valid if set(1)." 
        ::= { objectEntry 24590119 }
        
    rsDetector1CommunicationFailureValid    OBJECT-TYPE 
        SYNTAX INTEGER  { invalid(0),valid(1) } 
        ACCESS read-only 
        STATUS mandatory 
        DESCRIPTION 
            "Flag: 'Detector 1 communication failure' valid if set(1)." 
        ::= { objectEntry 24590120 }
        
    rsDetector1FailureValid                 OBJECT-TYPE 
        SYNTAX INTEGER  { invalid(0),valid(1) } 
        ACCESS read-only 
        STATUS mandatory 
        DESCRIPTION 
            "Flag: 'Detector 1 failure' valid if set(1)." 
        ::= { objectEntry 24590121 }
        
    rsChamber1DirtyValid                    OBJECT-TYPE 
        SYNTAX INTEGER  { invalid(0),valid(1) } 
        ACCESS read-only 
        STATUS mandatory 
        DESCRIPTION 
            "Flag: 'Detector 1 chamber dirty' valid if set(1)." 
        ::= { objectEntry 24590122 }
        
    rsAirFlowControlFailureValid            OBJECT-TYPE 
        SYNTAX INTEGER  { invalid(0),valid(1) } 
        ACCESS read-only 
        STATUS mandatory 
        DESCRIPTION 
            "Flag: 'Air flow control failure' valid if set(1)." 
        ::= { objectEntry 24590123 }
        
    rsStaticAirFlowLowValid                 OBJECT-TYPE 
        SYNTAX INTEGER  { invalid(0),valid(1) } 
        ACCESS read-only 
        STATUS mandatory 
        DESCRIPTION 
            "Flag: 'Static air flow rate low' valid if set(1)." 
        ::= { objectEntry 24590124 }
        
    rsStaticAirFlowHighValid                OBJECT-TYPE 
        SYNTAX INTEGER  { invalid(0),valid(1) } 
        ACCESS read-only 
        STATUS mandatory 
        DESCRIPTION 
            "Flag: 'Static air flow rate high' valid if set(1)." 
        ::= { objectEntry 24590125 }
        
    rsDynamicAirFlowLowValid                OBJECT-TYPE 
        SYNTAX INTEGER  { invalid(0),valid(1) } 
        ACCESS read-only 
        STATUS mandatory 
        DESCRIPTION 
            "Flag: 'Dynamic air flow rate low' valid if set(1)." 
        ::= { objectEntry 24590126 }
        
    rsDynamicAirFlowHighValid               OBJECT-TYPE 
        SYNTAX INTEGER  { invalid(0),valid(1) } 
        ACCESS read-only 
        STATUS mandatory 
        DESCRIPTION 
            "Flag: 'Dynamic air flow rate high' valid if set(1)." 
        ::= { objectEntry 24590127 }
        
    rsAirFlowInitAbortedValid               OBJECT-TYPE 
        SYNTAX INTEGER  { invalid(0),valid(1) } 
        ACCESS read-only 
        STATUS mandatory 
        DESCRIPTION 
            "Flag: 'Air flow initialization aborted' valid if set(1)." 
        ::= { objectEntry 24590128 }
        
    rsRoomIdentFailureValid                 OBJECT-TYPE 
        SYNTAX INTEGER  { invalid(0),valid(1) } 
        ACCESS read-only 
        STATUS mandatory 
        DESCRIPTION 
            "Flag: 'Room identification failure' valid if set(1)." 
        ::= { objectEntry 24590129 }
        
    rsDetector2CommunicationFailureValid    OBJECT-TYPE 
        SYNTAX INTEGER  { invalid(0),valid(1) } 
        ACCESS read-only 
        STATUS mandatory 
        DESCRIPTION 
            "Flag: 'Detector 2 communication failure' valid if set(1)." 
        ::= { objectEntry 24590130 }
        
    rsDetector2FailureValid                 OBJECT-TYPE 
        SYNTAX INTEGER  { invalid(0),valid(1) } 
        ACCESS read-only 
        STATUS mandatory 
        DESCRIPTION 
            "Flag: 'Detector 2 failure' valid if set(1)." 
        ::= { objectEntry 24590131 }
        
    rsChamber2DirtyValid                    OBJECT-TYPE 
        SYNTAX INTEGER  { invalid(0),valid(1) } 
        ACCESS read-only 
        STATUS mandatory 
        DESCRIPTION 
            "Flag: 'Detector 2 chamber dirty' valid if set(1)." 
        ::= { objectEntry 24590132 }
        
    rsTempSensor1Failure                    OBJECT-TYPE 
        SYNTAX INTEGER  { normal(0),failure(1) } 
        ACCESS read-only 
        STATUS mandatory 
        DESCRIPTION 
            "This flag is set(1) when the temperature sensor 1
             is outside it's allowed resistor range due to line shorts or broken lines." 
        ::= { objectEntry 24590133 }
        
    rsTempSensor2Failure                    OBJECT-TYPE 
        SYNTAX INTEGER  { off(0),on(1)} 
        ACCESS read-only 
        STATUS mandatory 
        DESCRIPTION 
            "This flag is set(1) when the temperature sensor 2
             is outside it's allowed resistor range due to line shorts or broken lines." 
        ::= { objectEntry 24590134 }
        
    rsTempSensor3Failure                    OBJECT-TYPE 
        SYNTAX INTEGER  { off(0),on(1)} 
        ACCESS read-only 
        STATUS mandatory 
        DESCRIPTION 
            "This flag is set(1) when the temperature sensor 3
             is outside it's allowed resistor range due to line shorts or broken lines." 
        ::= { objectEntry 24590135 }
        
    rsTempSensor4Failure                    OBJECT-TYPE 
        SYNTAX INTEGER  { off(0),on(1)} 
        ACCESS read-only 
        STATUS mandatory 
        DESCRIPTION 
            "This flag is set(1) when the temperature sensor 4
             is outside it's allowed resistor range due to line shorts or broken lines." 
        ::= { objectEntry 24590136 }
        
    rsTempSensor5Failure                    OBJECT-TYPE 
        SYNTAX INTEGER  { off(0),on(1)} 
        ACCESS read-only 
        STATUS mandatory 
        DESCRIPTION 
            "This flag is set(1) when the temperature sensor 5
             is outside it's allowed resistor range due to line shorts or broken lines." 
        ::= { objectEntry 24590137 }
        
    rsUnitHasInternalExtModule              OBJECT-TYPE 
        SYNTAX INTEGER  { off(0),on(1)} 
        ACCESS read-only 
        STATUS mandatory 
        DESCRIPTION 
            "This flag is set(1) when the unit has an extinguishing module built in." 
        ::= { objectEntry 24590138 }
        
    rsInternalExtModuleLacksValid           OBJECT-TYPE 
        SYNTAX INTEGER  { off(0),on(1)} 
        ACCESS read-only 
        STATUS mandatory 
        DESCRIPTION 
            "Flag: 'Internal extinguishing module lacks' valid if set(1)." 
        ::= { objectEntry 24590139 }
        
    rsInternalExtModuleLacks                OBJECT-TYPE 
        SYNTAX INTEGER  { off(0),on(1)} 
        ACCESS read-only 
        STATUS mandatory 
        DESCRIPTION 
            "This flag is set(1) when the built in extinguishing module is not present." 
        ::= { objectEntry 24590140 }
        
    rsInternalExtModuleLacksStored          OBJECT-TYPE 
        SYNTAX INTEGER  { off(0),on(1)} 
        ACCESS read-only 
        STATUS mandatory 
        DESCRIPTION 
            "Stored flag: Internal extinguishing module lacks." 
        ::= { objectEntry 24590141 }
        
    rsManualActivated                       OBJECT-TYPE 
        SYNTAX INTEGER  { off(0),on(1)} 
        ACCESS read-only 
        STATUS mandatory 
        DESCRIPTION 
            "This flag is set(1) when the unit is manual activated." 
        ::= { objectEntry 24590142 }
        
    rsMainAlarmSet                          OBJECT-TYPE 
        SYNTAX INTEGER  { off(0),on(1)} 
        ACCESS read-only 
        STATUS mandatory 
        DESCRIPTION 
            "This flag is set(1) when the fire alarm is set." 
        ::= { objectEntry 24590143 }
        
                
    ----------------------------------------------------
    -- Bits from RackSens data object 24623 (602F hex)
    ----------------------------------------------------

    rsBU01DoorSwitchExists                  OBJECT-TYPE 
        SYNTAX INTEGER  { no(0),yes(1) } 
        ACCESS read-only 
        STATUS mandatory 
        DESCRIPTION 
            "This flag is set(1) if the bus unit 1 has a door switch contact." 
        ::= { objectEntry 24623000 }
        
    rsBU01ManualActivationLineExists        OBJECT-TYPE 
        SYNTAX INTEGER  { no(0),yes(1) } 
        ACCESS read-only 
        STATUS mandatory 
        DESCRIPTION 
            "This flag is set(1) if the bus unit 1 has a manual activation line." 
        ::= { objectEntry 24623001 }
        
    rsBU01CutOffRelayExists                 OBJECT-TYPE 
        SYNTAX INTEGER  { no(0),yes(1) } 
        ACCESS read-only 
        STATUS mandatory 
        DESCRIPTION 
            "This flag is set(1) if the bus unit 1 has a cut-off relay." 
        ::= { objectEntry 24623002 }
        
    rsBU01IgnitionLineExists                OBJECT-TYPE 
        SYNTAX INTEGER  { no(0),yes(1) } 
        ACCESS read-only 
        STATUS mandatory 
        DESCRIPTION 
            "This flag is set(1) if the bus unit 1 has an ignition line." 
        ::= { objectEntry 24623003 }
        
    rsBU02DoorSwitchExists                  OBJECT-TYPE 
        SYNTAX INTEGER  { no(0),yes(1) } 
        ACCESS read-only 
        STATUS mandatory 
        DESCRIPTION 
            "This flag is set(1) if the bus unit 2 has a door switch contact." 
        ::= { objectEntry 24623004 }
        
    rsBU02ManualActivationLineExists        OBJECT-TYPE 
        SYNTAX INTEGER  { no(0),yes(1) } 
        ACCESS read-only 
        STATUS mandatory 
        DESCRIPTION 
            "This flag is set(1) if the bus unit 2 has a manual activation line." 
        ::= { objectEntry 24623005 }
        
    rsBU02CutOffRelayExists                 OBJECT-TYPE 
        SYNTAX INTEGER  { no(0),yes(1) } 
        ACCESS read-only 
        STATUS mandatory 
        DESCRIPTION 
            "This flag is set(1) if the bus unit 2 has a cut-off relay." 
        ::= { objectEntry 24623006 }
        
    rsBU02IgnitionLineExists                OBJECT-TYPE 
        SYNTAX INTEGER  { no(0),yes(1) } 
        ACCESS read-only 
        STATUS mandatory 
        DESCRIPTION 
            "This flag is set(1) if the bus unit 2 has an ignition line." 
        ::= { objectEntry 24623007 }
        
    rsBU03DoorSwitchExists                  OBJECT-TYPE 
        SYNTAX INTEGER  { no(0),yes(1) } 
        ACCESS read-only 
        STATUS mandatory 
        DESCRIPTION 
            "This flag is set(1) if the bus unit 3 has a door switch contact." 
        ::= { objectEntry 24623008 }
        
    rsBU03ManualActivationLineExists        OBJECT-TYPE 
        SYNTAX INTEGER  { no(0),yes(1) } 
        ACCESS read-only 
        STATUS mandatory 
        DESCRIPTION 
            "This flag is set(1) if the bus unit 3 has a manual activation line." 
        ::= { objectEntry 24623009 }
        
    rsBU03CutOffRelayExists                 OBJECT-TYPE 
        SYNTAX INTEGER  { no(0),yes(1) } 
        ACCESS read-only 
        STATUS mandatory 
        DESCRIPTION 
            "This flag is set(1) if the bus unit 3 has a cut-off relay." 
        ::= { objectEntry 24623010 }
        
    rsBU03IgnitionLineExists                OBJECT-TYPE 
        SYNTAX INTEGER  { no(0),yes(1) } 
        ACCESS read-only 
        STATUS mandatory 
        DESCRIPTION 
            "This flag is set(1) if the bus unit 3 has an ignition line." 
        ::= { objectEntry 24623011 }
        
    rsBU04DoorSwitchExists                  OBJECT-TYPE 
        SYNTAX INTEGER  { no(0),yes(1) } 
        ACCESS read-only 
        STATUS mandatory 
        DESCRIPTION 
            "This flag is set(1) if the bus unit 4 has a door switch contact." 
        ::= { objectEntry 24623012 }
        
    rsBU04ManualActivationLineExists        OBJECT-TYPE 
        SYNTAX INTEGER  { no(0),yes(1) } 
        ACCESS read-only 
        STATUS mandatory 
        DESCRIPTION 
            "This flag is set(1) if the bus unit 4 has a manual activation line." 
        ::= { objectEntry 24623013 }
        
    rsBU04CutOffRelayExists                 OBJECT-TYPE 
        SYNTAX INTEGER  { no(0),yes(1) } 
        ACCESS read-only 
        STATUS mandatory 
        DESCRIPTION 
            "This flag is set(1) if the bus unit 4 has a cut-off relay." 
        ::= { objectEntry 24623014 }
        
    rsBU04IgnitionLineExists                OBJECT-TYPE 
        SYNTAX INTEGER  { no(0),yes(1) } 
        ACCESS read-only 
        STATUS mandatory 
        DESCRIPTION 
            "This flag is set(1) if the bus unit 4 has an ignition line." 
        ::= { objectEntry 24623015 }
        
    rsBU05DoorSwitchExists                  OBJECT-TYPE 
        SYNTAX INTEGER  { no(0),yes(1) } 
        ACCESS read-only 
        STATUS mandatory 
        DESCRIPTION 
            "This flag is set(1) if the bus unit 5 has a door switch contact." 
        ::= { objectEntry 24623016 }
        
    rsBU05ManualActivationLineExists        OBJECT-TYPE 
        SYNTAX INTEGER  { no(0),yes(1) } 
        ACCESS read-only 
        STATUS mandatory 
        DESCRIPTION 
            "This flag is set(1) if the bus unit 5 has a manual activation line." 
        ::= { objectEntry 24623017 }
        
    rsBU05CutOffRelayExists                 OBJECT-TYPE 
        SYNTAX INTEGER  { no(0),yes(1) } 
        ACCESS read-only 
        STATUS mandatory 
        DESCRIPTION 
            "This flag is set(1) if the bus unit 5 has a cut-off relay." 
        ::= { objectEntry 24623018 }
        
    rsBU05IgnitionLineExists                OBJECT-TYPE 
        SYNTAX INTEGER  { no(0),yes(1) } 
        ACCESS read-only 
        STATUS mandatory 
        DESCRIPTION 
            "This flag is set(1) if the bus unit 5 has an ignition line." 
        ::= { objectEntry 24623019 }
        
    rsBU06DoorSwitchExists                  OBJECT-TYPE 
        SYNTAX INTEGER  { no(0),yes(1) } 
        ACCESS read-only 
        STATUS mandatory 
        DESCRIPTION 
            "This flag is set(1) if the bus unit 6 has a door switch contact." 
        ::= { objectEntry 24623020 }
        
    rsBU06ManualActivationLineExists        OBJECT-TYPE 
        SYNTAX INTEGER  { no(0),yes(1) } 
        ACCESS read-only 
        STATUS mandatory 
        DESCRIPTION 
            "This flag is set(1) if the bus unit 6 has a manual activation line." 
        ::= { objectEntry 24623021 }
        
    rsBU06CutOffRelayExists                 OBJECT-TYPE 
        SYNTAX INTEGER  { no(0),yes(1) } 
        ACCESS read-only 
        STATUS mandatory 
        DESCRIPTION 
            "This flag is set(1) if the bus unit 6 has a cut-off relay." 
        ::= { objectEntry 24623022 }
        
    rsBU06IgnitionLineExists                OBJECT-TYPE 
        SYNTAX INTEGER  { no(0),yes(1) } 
        ACCESS read-only 
        STATUS mandatory 
        DESCRIPTION 
            "This flag is set(1) if the bus unit 6 has an ignition line." 
        ::= { objectEntry 24623023 }
        
    rsBU07DoorSwitchExists                  OBJECT-TYPE 
        SYNTAX INTEGER  { no(0),yes(1) } 
        ACCESS read-only 
        STATUS mandatory 
        DESCRIPTION 
            "This flag is set(1) if the bus unit 7 has a door switch contact." 
        ::= { objectEntry 24623024 }
        
    rsBU07ManualActivationLineExists        OBJECT-TYPE 
        SYNTAX INTEGER  { no(0),yes(1) } 
        ACCESS read-only 
        STATUS mandatory 
        DESCRIPTION 
            "This flag is set(1) if the bus unit 7 has a manual activation line." 
        ::= { objectEntry 24623025 }
        
    rsBU07CutOffRelayExists                 OBJECT-TYPE 
        SYNTAX INTEGER  { no(0),yes(1) } 
        ACCESS read-only 
        STATUS mandatory 
        DESCRIPTION 
            "This flag is set(1) if the bus unit 7 has a cut-off relay." 
        ::= { objectEntry 24623026 }
        
    rsBU07IgnitionLineExists                OBJECT-TYPE 
        SYNTAX INTEGER  { no(0),yes(1) } 
        ACCESS read-only 
        STATUS mandatory 
        DESCRIPTION 
            "This flag is set(1) if the bus unit 7 has an ignition line." 
        ::= { objectEntry 24623027 }
        
    rsBU08DoorSwitchExists                  OBJECT-TYPE 
        SYNTAX INTEGER  { no(0),yes(1) } 
        ACCESS read-only 
        STATUS mandatory 
        DESCRIPTION 
            "This flag is set(1) if the bus unit 8 has a door switch contact." 
        ::= { objectEntry 24623028 }
        
    rsBU08ManualActivationLineExists        OBJECT-TYPE 
        SYNTAX INTEGER  { no(0),yes(1) } 
        ACCESS read-only 
        STATUS mandatory 
        DESCRIPTION 
            "This flag is set(1) if the bus unit 8 has a manual activation line." 
        ::= { objectEntry 24623029 }
        
    rsBU08CutOffRelayExists                 OBJECT-TYPE 
        SYNTAX INTEGER  { no(0),yes(1) } 
        ACCESS read-only 
        STATUS mandatory 
        DESCRIPTION 
            "This flag is set(1) if the bus unit 8 has a cut-off relay." 
        ::= { objectEntry 24623030 }
        
    rsBU08IgnitionLineExists                OBJECT-TYPE 
        SYNTAX INTEGER  { no(0),yes(1) } 
        ACCESS read-only 
        STATUS mandatory 
        DESCRIPTION 
            "This flag is set(1) if the bus unit 8 has an ignition line." 
        ::= { objectEntry 24623031 }
        
    rsBU09DoorSwitchExists                  OBJECT-TYPE 
        SYNTAX INTEGER  { no(0),yes(1) } 
        ACCESS read-only 
        STATUS mandatory 
        DESCRIPTION 
            "This flag is set(1) if the bus unit 9 has a door switch contact." 
        ::= { objectEntry 24623032 }
        
    rsBU09ManualActivationLineExists        OBJECT-TYPE 
        SYNTAX INTEGER  { no(0),yes(1) } 
        ACCESS read-only 
        STATUS mandatory 
        DESCRIPTION 
            "This flag is set(1) if the bus unit 9 has a manual activation line." 
        ::= { objectEntry 24623033 }
        
    rsBU09CutOffRelayExists                 OBJECT-TYPE 
        SYNTAX INTEGER  { no(0),yes(1) } 
        ACCESS read-only 
        STATUS mandatory 
        DESCRIPTION 
            "This flag is set(1) if the bus unit 9 has a cut-off relay." 
        ::= { objectEntry 24623034 }
        
    rsBU09IgnitionLineExists                OBJECT-TYPE 
        SYNTAX INTEGER  { no(0),yes(1) } 
        ACCESS read-only 
        STATUS mandatory 
        DESCRIPTION 
            "This flag is set(1) if the bus unit 9 has an ignition line." 
        ::= { objectEntry 24623035 }
        
    rsBU10DoorSwitchExists                  OBJECT-TYPE 
        SYNTAX INTEGER  { no(0),yes(1) } 
        ACCESS read-only 
        STATUS mandatory 
        DESCRIPTION 
            "This flag is set(1) if the bus unit 10 has a door switch contact." 
        ::= { objectEntry 24623036 }
        
    rsBU10ManualActivationLineExists        OBJECT-TYPE 
        SYNTAX INTEGER  { no(0),yes(1) } 
        ACCESS read-only 
        STATUS mandatory 
        DESCRIPTION 
            "This flag is set(1) if the bus unit 10 has a manual activation line." 
        ::= { objectEntry 24623037 }
        
    rsBU10CutOffRelayExists                 OBJECT-TYPE 
        SYNTAX INTEGER  { no(0),yes(1) } 
        ACCESS read-only 
        STATUS mandatory 
        DESCRIPTION 
            "This flag is set(1) if the bus unit 10 has a cut-off relay." 
        ::= { objectEntry 24623038 }
        
    rsBU10IgnitionLineExists                OBJECT-TYPE 
        SYNTAX INTEGER  { no(0),yes(1) } 
        ACCESS read-only 
        STATUS mandatory 
        DESCRIPTION 
            "This flag is set(1) if the bus unit 10 has an ignition line." 
        ::= { objectEntry 24623039 }
        
    rsBU01ProgramFailure                    OBJECT-TYPE 
        SYNTAX INTEGER  { normal(0),failure(1) } 
        ACCESS read-only 
        STATUS mandatory 
        DESCRIPTION 
            "This flag is set(1) when in bus unit 1
             a program or memory failure is detected." 
        ::= { objectEntry 24623040 }
        
    rsBU01AgentLoss                         OBJECT-TYPE 
        SYNTAX INTEGER  { normal(0),loss(1) } 
        ACCESS read-only 
        STATUS mandatory 
        DESCRIPTION 
            "This flag is set(1) when in bus unit 1
             the pressure sensor detects agent loss." 
        ::= { objectEntry 24623041 }
        
    rsBU01SupplyVoltageLow                  OBJECT-TYPE 
        SYNTAX INTEGER  { normal(0),low(1) } 
        ACCESS read-only 
        STATUS mandatory 
        DESCRIPTION 
            "This flag is set(1) when in bus unit 1
             the supply voltage of the unit is too low." 
        ::= { objectEntry 24623042 }
        
    rsBU01IgnitionVoltageLow                OBJECT-TYPE 
        SYNTAX INTEGER  { normal(0),low(1) } 
        ACCESS read-only 
        STATUS mandatory 
        DESCRIPTION 
            "This flag is set(1) when in bus unit 1
             the ignition voltage of the unit is too low." 
        ::= { objectEntry 24623043 }
        
    rsBU01CutOffLineFailure                 OBJECT-TYPE 
        SYNTAX INTEGER  { normal(0),failure(1) } 
        ACCESS read-only 
        STATUS mandatory 
        DESCRIPTION 
            "This flag is set(1) when in bus unit 1
             the resistor of the cut-off line is outside 
             it's allowed range due to line shorts or broken lines." 
        ::= { objectEntry 24623044 }
        
    rsBU01IgnitionLineFailure               OBJECT-TYPE 
        SYNTAX INTEGER  { normal(0),failure(1) } 
        ACCESS read-only 
        STATUS mandatory 
        DESCRIPTION 
            "This flag is set(1) when in bus unit 1
             the resistor of the ignition line is outside 
             it's allowed range due to line shorts or broken lines." 
        ::= { objectEntry 24623045 }
        
    rsBU01ManActivationLineFailure          OBJECT-TYPE 
        SYNTAX INTEGER  { normal(0),failure(1) } 
        ACCESS read-only 
        STATUS mandatory 
        DESCRIPTION 
            "This flag is set(1) when in bus unit 1
             the resistor of the manual activation line is outside 
             it's allowed range due to line shorts or broken lines." 
        ::= { objectEntry 24623046 }
        
    rsBU01Failure                           OBJECT-TYPE 
        SYNTAX INTEGER  { normal(0),failure(1) } 
        ACCESS read-only 
        STATUS mandatory 
        DESCRIPTION 
            "This flag is set(1) when in bus unit 1
             a failure is detected." 
        ::= { objectEntry 24623047 }
        
    rsBU02ProgramFailure                    OBJECT-TYPE 
        SYNTAX INTEGER  { normal(0),failure(1) } 
        ACCESS read-only 
        STATUS mandatory 
        DESCRIPTION 
            "This flag is set(1) when in bus unit 2
             a program or memory failure is detected." 
        ::= { objectEntry 24623048 }
        
    rsBU02AgentLoss                         OBJECT-TYPE 
        SYNTAX INTEGER  { normal(0),loss(1) } 
        ACCESS read-only 
        STATUS mandatory 
        DESCRIPTION 
            "This flag is set(1) when in bus unit 2
             the pressure sensor detects agent loss." 
        ::= { objectEntry 24623049 }
        
    rsBU02SupplyVoltageLow                  OBJECT-TYPE 
        SYNTAX INTEGER  { normal(0),low(1) } 
        ACCESS read-only 
        STATUS mandatory 
        DESCRIPTION 
            "This flag is set(1) when in bus unit 2
             the supply voltage of the unit is too low." 
        ::= { objectEntry 24623050 }
        
    rsBU02IgnitionVoltageLow                OBJECT-TYPE 
        SYNTAX INTEGER  { normal(0),low(1) } 
        ACCESS read-only 
        STATUS mandatory 
        DESCRIPTION 
            "This flag is set(1) when in bus unit 2
             the ignition voltage of the unit is too low." 
        ::= { objectEntry 24623051 }
        
    rsBU02CutOffLineFailure                 OBJECT-TYPE 
        SYNTAX INTEGER  { normal(0),failure(1) } 
        ACCESS read-only 
        STATUS mandatory 
        DESCRIPTION 
            "This flag is set(1) when in bus unit 2
             the resistor of the cut-off line is outside 
             it's allowed range due to line shorts or broken lines." 
        ::= { objectEntry 24623052 }
        
    rsBU02IgnitionLineFailure               OBJECT-TYPE 
        SYNTAX INTEGER  { normal(0),failure(1) } 
        ACCESS read-only 
        STATUS mandatory 
        DESCRIPTION 
            "This flag is set(1) when in bus unit 2
             the resistor of the ignition line is outside 
             it's allowed range due to line shorts or broken lines." 
        ::= { objectEntry 24623053 }
        
    rsBU02ManActivationLineFailure          OBJECT-TYPE 
        SYNTAX INTEGER  { normal(0),failure(1) } 
        ACCESS read-only 
        STATUS mandatory 
        DESCRIPTION 
            "This flag is set(1) when in bus unit 2
             the resistor of the manual activation line is outside 
             it's allowed range due to line shorts or broken lines." 
        ::= { objectEntry 24623054 }
        
    rsBU02Failure                           OBJECT-TYPE 
        SYNTAX INTEGER  { normal(0),failure(1) } 
        ACCESS read-only 
        STATUS mandatory 
        DESCRIPTION 
            "This flag is set(1) when in bus unit 2
             a failure is detected." 
        ::= { objectEntry 24623055 }
        
    rsBU03ProgramFailure                    OBJECT-TYPE 
        SYNTAX INTEGER  { normal(0),failure(1) } 
        ACCESS read-only 
        STATUS mandatory 
        DESCRIPTION 
            "This flag is set(1) when in bus unit 3
             a program or memory failure is detected." 
        ::= { objectEntry 24623056 }
        
    rsBU03AgentLoss                         OBJECT-TYPE 
        SYNTAX INTEGER  { normal(0),loss(1) } 
        ACCESS read-only 
        STATUS mandatory 
        DESCRIPTION 
            "This flag is set(1) when in bus unit 3
             the pressure sensor detects agent loss." 
        ::= { objectEntry 24623057 }
        
    rsBU03SupplyVoltageLow                  OBJECT-TYPE 
        SYNTAX INTEGER  { normal(0),low(1) } 
        ACCESS read-only 
        STATUS mandatory 
        DESCRIPTION 
            "This flag is set(1) when in bus unit 3
             the supply voltage of the unit is too low." 
        ::= { objectEntry 24623058 }
        
    rsBU03IgnitionVoltageLow                OBJECT-TYPE 
        SYNTAX INTEGER  { normal(0),low(1) } 
        ACCESS read-only 
        STATUS mandatory 
        DESCRIPTION 
            "This flag is set(1) when in bus unit 3
             the ignition voltage of the unit is too low." 
        ::= { objectEntry 24623059 }
        
    rsBU03CutOffLineFailure                 OBJECT-TYPE 
        SYNTAX INTEGER  { normal(0),failure(1) } 
        ACCESS read-only 
        STATUS mandatory 
        DESCRIPTION 
            "This flag is set(1) when in bus unit 3
             the resistor of the cut-off line is outside 
             it's allowed range due to line shorts or broken lines." 
        ::= { objectEntry 24623060 }
        
    rsBU03IgnitionLineFailure               OBJECT-TYPE 
        SYNTAX INTEGER  { normal(0),failure(1) } 
        ACCESS read-only 
        STATUS mandatory 
        DESCRIPTION 
            "This flag is set(1) when in bus unit 3
             the resistor of the ignition line is outside 
             it's allowed range due to line shorts or broken lines." 
        ::= { objectEntry 24623061 }
        
    rsBU03ManActivationLineFailure          OBJECT-TYPE 
        SYNTAX INTEGER  { normal(0),failure(1) } 
        ACCESS read-only 
        STATUS mandatory 
        DESCRIPTION 
            "This flag is set(1) when in bus unit 3
             the resistor of the manual activation line is outside 
             it's allowed range due to line shorts or broken lines." 
        ::= { objectEntry 24623062 }
        
    rsBU03Failure                           OBJECT-TYPE 
        SYNTAX INTEGER  { normal(0),failure(1) } 
        ACCESS read-only 
        STATUS mandatory 
        DESCRIPTION 
            "This flag is set(1) when in bus unit 3
             a failure is detected." 
        ::= { objectEntry 24623063 }
        
    rsBU04ProgramFailure                    OBJECT-TYPE 
        SYNTAX INTEGER  { normal(0),failure(1) } 
        ACCESS read-only 
        STATUS mandatory 
        DESCRIPTION 
            "This flag is set(1) when in bus unit 4
             a program or memory failure is detected." 
        ::= { objectEntry 24623064 }
        
    rsBU04AgentLoss                         OBJECT-TYPE 
        SYNTAX INTEGER  { normal(0),loss(1) } 
        ACCESS read-only 
        STATUS mandatory 
        DESCRIPTION 
            "This flag is set(1) when in bus unit 4
             the pressure sensor detects agent loss." 
        ::= { objectEntry 24623065 }
        
    rsBU04SupplyVoltageLow                  OBJECT-TYPE 
        SYNTAX INTEGER  { normal(0),low(1) } 
        ACCESS read-only 
        STATUS mandatory 
        DESCRIPTION 
            "This flag is set(1) when in bus unit 4
             the supply voltage of the unit is too low." 
        ::= { objectEntry 24623066 }
        
    rsBU04IgnitionVoltageLow                OBJECT-TYPE 
        SYNTAX INTEGER  { normal(0),low(1) } 
        ACCESS read-only 
        STATUS mandatory 
        DESCRIPTION 
            "This flag is set(1) when in bus unit 4
             the ignition voltage of the unit is too low." 
        ::= { objectEntry 24623067 }
        
    rsBU04CutOffLineFailure                 OBJECT-TYPE 
        SYNTAX INTEGER  { normal(0),failure(1) } 
        ACCESS read-only 
        STATUS mandatory 
        DESCRIPTION 
            "This flag is set(1) when in bus unit 4
             the resistor of the cut-off line is outside 
             it's allowed range due to line shorts or broken lines." 
        ::= { objectEntry 24623068 }
        
    rsBU04IgnitionLineFailure               OBJECT-TYPE 
        SYNTAX INTEGER  { normal(0),failure(1) } 
        ACCESS read-only 
        STATUS mandatory 
        DESCRIPTION 
            "This flag is set(1) when in bus unit 4
             the resistor of the ignition line is outside 
             it's allowed range due to line shorts or broken lines." 
        ::= { objectEntry 24623069 }
        
    rsBU04ManActivationLineFailure          OBJECT-TYPE 
        SYNTAX INTEGER  { normal(0),failure(1) } 
        ACCESS read-only 
        STATUS mandatory 
        DESCRIPTION 
            "This flag is set(1) when in bus unit 4
             the resistor of the manual activation line is outside 
             it's allowed range due to line shorts or broken lines." 
        ::= { objectEntry 24623070 }
        
    rsBU04Failure                           OBJECT-TYPE 
        SYNTAX INTEGER  { normal(0),failure(1) } 
        ACCESS read-only 
        STATUS mandatory 
        DESCRIPTION 
            "This flag is set(1) when in bus unit 4
             a failure is detected." 
        ::= { objectEntry 24623071 }
        
    rsBU05ProgramFailure                    OBJECT-TYPE 
        SYNTAX INTEGER  { normal(0),failure(1) } 
        ACCESS read-only 
        STATUS mandatory 
        DESCRIPTION 
            "This flag is set(1) when in bus unit 5
             a program or memory failure is detected." 
        ::= { objectEntry 24623072 }
        
    rsBU05AgentLoss                         OBJECT-TYPE 
        SYNTAX INTEGER  { normal(0),loss(1) } 
        ACCESS read-only 
        STATUS mandatory 
        DESCRIPTION 
            "This flag is set(1) when in bus unit 5
             the pressure sensor detects agent loss." 
        ::= { objectEntry 24623073 }
        
    rsBU05SupplyVoltageLow                  OBJECT-TYPE 
        SYNTAX INTEGER  { normal(0),low(1) } 
        ACCESS read-only 
        STATUS mandatory 
        DESCRIPTION 
            "This flag is set(1) when in bus unit 5
             the supply voltage of the unit is too low." 
        ::= { objectEntry 24623074 }
        
    rsBU05IgnitionVoltageLow                OBJECT-TYPE 
        SYNTAX INTEGER  { normal(0),low(1) } 
        ACCESS read-only 
        STATUS mandatory 
        DESCRIPTION 
            "This flag is set(1) when in bus unit 5
             the ignition voltage of the unit is too low." 
        ::= { objectEntry 24623075 }
        
    rsBU05CutOffLineFailure                 OBJECT-TYPE 
        SYNTAX INTEGER  { normal(0),failure(1) } 
        ACCESS read-only 
        STATUS mandatory 
        DESCRIPTION 
            "This flag is set(1) when in bus unit 5
             the resistor of the cut-off line is outside 
             it's allowed range due to line shorts or broken lines." 
        ::= { objectEntry 24623076 }
        
    rsBU05IgnitionLineFailure               OBJECT-TYPE 
        SYNTAX INTEGER  { normal(0),failure(1) } 
        ACCESS read-only 
        STATUS mandatory 
        DESCRIPTION 
            "This flag is set(1) when in bus unit 5
             the resistor of the ignition line is outside 
             it's allowed range due to line shorts or broken lines." 
        ::= { objectEntry 24623077 }
        
    rsBU05ManActivationLineFailure          OBJECT-TYPE 
        SYNTAX INTEGER  { normal(0),failure(1) } 
        ACCESS read-only 
        STATUS mandatory 
        DESCRIPTION 
            "This flag is set(1) when in bus unit 5
             the resistor of the manual activation line is outside 
             it's allowed range due to line shorts or broken lines." 
        ::= { objectEntry 24623078 }
        
    rsBU05Failure                           OBJECT-TYPE 
        SYNTAX INTEGER  { normal(0),failure(1) } 
        ACCESS read-only 
        STATUS mandatory 
        DESCRIPTION 
            "This flag is set(1) when in bus unit 5
             a failure is detected." 
        ::= { objectEntry 24623079 }
        
    rsBU06ProgramFailure                    OBJECT-TYPE 
        SYNTAX INTEGER  { normal(0),failure(1) } 
        ACCESS read-only 
        STATUS mandatory 
        DESCRIPTION 
            "This flag is set(1) when in bus unit 6
             a program or memory failure is detected." 
        ::= { objectEntry 24623080 }
        
    rsBU06AgentLoss                         OBJECT-TYPE 
        SYNTAX INTEGER  { normal(0),loss(1) } 
        ACCESS read-only 
        STATUS mandatory 
        DESCRIPTION 
            "This flag is set(1) when in bus unit 6
             the pressure sensor detects agent loss." 
        ::= { objectEntry 24623081 }
        
    rsBU06SupplyVoltageLow                  OBJECT-TYPE 
        SYNTAX INTEGER  { normal(0),low(1) } 
        ACCESS read-only 
        STATUS mandatory 
        DESCRIPTION 
            "This flag is set(1) when in bus unit 6
             the supply voltage of the unit is too low." 
        ::= { objectEntry 24623082 }
        
    rsBU06IgnitionVoltageLow                OBJECT-TYPE 
        SYNTAX INTEGER  { normal(0),low(1) } 
        ACCESS read-only 
        STATUS mandatory 
        DESCRIPTION 
            "This flag is set(1) when in bus unit 6
             the ignition voltage of the unit is too low." 
        ::= { objectEntry 24623083 }
        
    rsBU06CutOffLineFailure                 OBJECT-TYPE 
        SYNTAX INTEGER  { normal(0),failure(1) } 
        ACCESS read-only 
        STATUS mandatory 
        DESCRIPTION 
            "This flag is set(1) when in bus unit 6
             the resistor of the cut-off line is outside 
             it's allowed range due to line shorts or broken lines." 
        ::= { objectEntry 24623084 }
        
    rsBU06IgnitionLineFailure               OBJECT-TYPE 
        SYNTAX INTEGER  { normal(0),failure(1) } 
        ACCESS read-only 
        STATUS mandatory 
        DESCRIPTION 
            "This flag is set(1) when in bus unit 6
             the resistor of the ignition line is outside 
             it's allowed range due to line shorts or broken lines." 
        ::= { objectEntry 24623085 }
        
    rsBU06ManActivationLineFailure          OBJECT-TYPE 
        SYNTAX INTEGER  { normal(0),failure(1) } 
        ACCESS read-only 
        STATUS mandatory 
        DESCRIPTION 
            "This flag is set(1) when in bus unit 6
             the resistor of the manual activation line is outside 
             it's allowed range due to line shorts or broken lines." 
        ::= { objectEntry 24623086 }
        
    rsBU06Failure                           OBJECT-TYPE 
        SYNTAX INTEGER  { normal(0),failure(1) } 
        ACCESS read-only 
        STATUS mandatory 
        DESCRIPTION 
            "This flag is set(1) when in bus unit 6
             a failure is detected." 
        ::= { objectEntry 24623087 }
        
    rsBU07ProgramFailure                    OBJECT-TYPE 
        SYNTAX INTEGER  { normal(0),failure(1) } 
        ACCESS read-only 
        STATUS mandatory 
        DESCRIPTION 
            "This flag is set(1) when in bus unit 7
             a program or memory failure is detected." 
        ::= { objectEntry 24623088 }
        
    rsBU07AgentLoss                         OBJECT-TYPE 
        SYNTAX INTEGER  { normal(0),loss(1) } 
        ACCESS read-only 
        STATUS mandatory 
        DESCRIPTION 
            "This flag is set(1) when in bus unit 7
             the pressure sensor detects agent loss." 
        ::= { objectEntry 24623089 }
        
    rsBU07SupplyVoltageLow                  OBJECT-TYPE 
        SYNTAX INTEGER  { normal(0),low(1) } 
        ACCESS read-only 
        STATUS mandatory 
        DESCRIPTION 
            "This flag is set(1) when in bus unit 7
             the supply voltage of the unit is too low." 
        ::= { objectEntry 24623090 }
        
    rsBU07IgnitionVoltageLow                OBJECT-TYPE 
        SYNTAX INTEGER  { normal(0),low(1) } 
        ACCESS read-only 
        STATUS mandatory 
        DESCRIPTION 
            "This flag is set(1) when in bus unit 7
             the ignition voltage of the unit is too low." 
        ::= { objectEntry 24623091 }
        
    rsBU07CutOffLineFailure                 OBJECT-TYPE 
        SYNTAX INTEGER  { normal(0),failure(1) } 
        ACCESS read-only 
        STATUS mandatory 
        DESCRIPTION 
            "This flag is set(1) when in bus unit 7
             the resistor of the cut-off line is outside 
             it's allowed range due to line shorts or broken lines." 
        ::= { objectEntry 24623092 }
        
    rsBU07IgnitionLineFailure               OBJECT-TYPE 
        SYNTAX INTEGER  { normal(0),failure(1) } 
        ACCESS read-only 
        STATUS mandatory 
        DESCRIPTION 
            "This flag is set(1) when in bus unit 7
             the resistor of the ignition line is outside 
             it's allowed range due to line shorts or broken lines." 
        ::= { objectEntry 24623093 }
        
    rsBU07ManActivationLineFailure          OBJECT-TYPE 
        SYNTAX INTEGER  { normal(0),failure(1) } 
        ACCESS read-only 
        STATUS mandatory 
        DESCRIPTION 
            "This flag is set(1) when in bus unit 7
             the resistor of the manual activation line is outside 
             it's allowed range due to line shorts or broken lines." 
        ::= { objectEntry 24623094 }
        
    rsBU07Failure                           OBJECT-TYPE 
        SYNTAX INTEGER  { normal(0),failure(1) } 
        ACCESS read-only 
        STATUS mandatory 
        DESCRIPTION 
            "This flag is set(1) when in bus unit 7
             a failure is detected." 
        ::= { objectEntry 24623095 }
        
    rsBU08ProgramFailure                    OBJECT-TYPE 
        SYNTAX INTEGER  { normal(0),failure(1) } 
        ACCESS read-only 
        STATUS mandatory 
        DESCRIPTION 
            "This flag is set(1) when in bus unit 8
             a program or memory failure is detected." 
        ::= { objectEntry 24623096 }
        
    rsBU08AgentLoss                         OBJECT-TYPE 
        SYNTAX INTEGER  { normal(0),loss(1) } 
        ACCESS read-only 
        STATUS mandatory 
        DESCRIPTION 
            "This flag is set(1) when in bus unit 8
             the pressure sensor detects agent loss." 
        ::= { objectEntry 24623097 }
        
    rsBU08SupplyVoltageLow                  OBJECT-TYPE 
        SYNTAX INTEGER  { normal(0),low(1) } 
        ACCESS read-only 
        STATUS mandatory 
        DESCRIPTION 
            "This flag is set(1) when in bus unit 8
             the supply voltage of the unit is too low." 
        ::= { objectEntry 24623098 }
        
    rsBU08IgnitionVoltageLow                OBJECT-TYPE 
        SYNTAX INTEGER  { normal(0),low(1) } 
        ACCESS read-only 
        STATUS mandatory 
        DESCRIPTION 
            "This flag is set(1) when in bus unit 8
             the ignition voltage of the unit is too low." 
        ::= { objectEntry 24623099 }
        
    rsBU08CutOffLineFailure                 OBJECT-TYPE 
        SYNTAX INTEGER  { normal(0),failure(1) } 
        ACCESS read-only 
        STATUS mandatory 
        DESCRIPTION 
            "This flag is set(1) when in bus unit 8
             the resistor of the cut-off line is outside 
             it's allowed range due to line shorts or broken lines." 
        ::= { objectEntry 24623100 }
        
    rsBU08IgnitionLineFailure               OBJECT-TYPE 
        SYNTAX INTEGER  { normal(0),failure(1) } 
        ACCESS read-only 
        STATUS mandatory 
        DESCRIPTION 
            "This flag is set(1) when in bus unit 8
             the resistor of the ignition line is outside 
             it's allowed range due to line shorts or broken lines." 
        ::= { objectEntry 24623101 }
        
    rsBU08ManActivationLineFailure          OBJECT-TYPE 
        SYNTAX INTEGER  { normal(0),failure(1) } 
        ACCESS read-only 
        STATUS mandatory 
        DESCRIPTION 
            "This flag is set(1) when in bus unit 8
             the resistor of the manual activation line is outside 
             it's allowed range due to line shorts or broken lines." 
        ::= { objectEntry 24623102 }
        
    rsBU08Failure                           OBJECT-TYPE 
        SYNTAX INTEGER  { normal(0),failure(1) } 
        ACCESS read-only 
        STATUS mandatory 
        DESCRIPTION 
            "This flag is set(1) when in bus unit 8
             a failure is detected." 
        ::= { objectEntry 24623103 }
        
    rsBU09ProgramFailure                    OBJECT-TYPE 
        SYNTAX INTEGER  { normal(0),failure(1) } 
        ACCESS read-only 
        STATUS mandatory 
        DESCRIPTION 
            "This flag is set(1) when in bus unit 9
             a program or memory failure is detected." 
        ::= { objectEntry 24623104 }
        
    rsBU09AgentLoss                         OBJECT-TYPE 
        SYNTAX INTEGER  { normal(0),loss(1) } 
        ACCESS read-only 
        STATUS mandatory 
        DESCRIPTION 
            "This flag is set(1) when in bus unit 9
             the pressure sensor detects agent loss." 
        ::= { objectEntry 24623105 }
        
    rsBU09SupplyVoltageLow                  OBJECT-TYPE 
        SYNTAX INTEGER  { normal(0),low(1) } 
        ACCESS read-only 
        STATUS mandatory 
        DESCRIPTION 
            "This flag is set(1) when in bus unit 9
             the supply voltage of the unit is too low." 
        ::= { objectEntry 24623106 }
        
    rsBU09IgnitionVoltageLow                OBJECT-TYPE 
        SYNTAX INTEGER  { normal(0),low(1) } 
        ACCESS read-only 
        STATUS mandatory 
        DESCRIPTION 
            "This flag is set(1) when in bus unit 9
             the ignition voltage of the unit is too low." 
        ::= { objectEntry 24623107 }
        
    rsBU09CutOffLineFailure                 OBJECT-TYPE 
        SYNTAX INTEGER  { normal(0),failure(1) } 
        ACCESS read-only 
        STATUS mandatory 
        DESCRIPTION 
            "This flag is set(1) when in bus unit 9
             the resistor of the cut-off line is outside 
             it's allowed range due to line shorts or broken lines." 
        ::= { objectEntry 24623108 }
        
    rsBU09IgnitionLineFailure               OBJECT-TYPE 
        SYNTAX INTEGER  { normal(0),failure(1) } 
        ACCESS read-only 
        STATUS mandatory 
        DESCRIPTION 
            "This flag is set(1) when in bus unit 9
             the resistor of the ignition line is outside 
             it's allowed range due to line shorts or broken lines." 
        ::= { objectEntry 24623109 }
        
    rsBU09ManActivationLineFailure          OBJECT-TYPE 
        SYNTAX INTEGER  { normal(0),failure(1) } 
        ACCESS read-only 
        STATUS mandatory 
        DESCRIPTION 
            "This flag is set(1) when in bus unit 9
             the resistor of the manual activation line is outside 
             it's allowed range due to line shorts or broken lines." 
        ::= { objectEntry 24623110 }
        
    rsBU09Failure                           OBJECT-TYPE 
        SYNTAX INTEGER  { normal(0),failure(1) } 
        ACCESS read-only 
        STATUS mandatory 
        DESCRIPTION 
            "This flag is set(1) when in bus unit 9
             a failure is detected." 
        ::= { objectEntry 24623111 }
        
    rsBU10ProgramFailure                    OBJECT-TYPE 
        SYNTAX INTEGER  { normal(0),failure(1) } 
        ACCESS read-only 
        STATUS mandatory 
        DESCRIPTION 
            "This flag is set(1) when in bus unit 10
             a program or memory failure is detected." 
        ::= { objectEntry 24623112 }
        
    rsBU10AgentLoss                         OBJECT-TYPE 
        SYNTAX INTEGER  { normal(0),loss(1) } 
        ACCESS read-only 
        STATUS mandatory 
        DESCRIPTION 
            "This flag is set(1) when in bus unit 10
             the pressure sensor detects agent loss." 
        ::= { objectEntry 24623113 }
        
    rsBU10SupplyVoltageLow                  OBJECT-TYPE 
        SYNTAX INTEGER  { normal(0),low(1) } 
        ACCESS read-only 
        STATUS mandatory 
        DESCRIPTION 
            "This flag is set(1) when in bus unit 10
             the supply voltage of the unit is too low." 
        ::= { objectEntry 24623114 }
        
    rsBU10IgnitionVoltageLow                OBJECT-TYPE 
        SYNTAX INTEGER  { normal(0),low(1) } 
        ACCESS read-only 
        STATUS mandatory 
        DESCRIPTION 
            "This flag is set(1) when in bus unit 10
             the ignition voltage of the unit is too low." 
        ::= { objectEntry 24623115 }
        
    rsBU10CutOffLineFailure                 OBJECT-TYPE 
        SYNTAX INTEGER  { normal(0),failure(1) } 
        ACCESS read-only 
        STATUS mandatory 
        DESCRIPTION 
            "This flag is set(1) when in bus unit 10
             the resistor of the cut-off line is outside 
             it's allowed range due to line shorts or broken lines." 
        ::= { objectEntry 24623116 }
        
    rsBU10IgnitionLineFailure               OBJECT-TYPE 
        SYNTAX INTEGER  { normal(0),failure(1) } 
        ACCESS read-only 
        STATUS mandatory 
        DESCRIPTION 
            "This flag is set(1) when in bus unit 10
             the resistor of the ignition line is outside 
             it's allowed range due to line shorts or broken lines." 
        ::= { objectEntry 24623117 }
        
    rsBU10ManActivationLineFailure          OBJECT-TYPE 
        SYNTAX INTEGER  { normal(0),failure(1) } 
        ACCESS read-only 
        STATUS mandatory 
        DESCRIPTION 
            "This flag is set(1) when in bus unit 10
             the resistor of the manual activation line is outside 
             it's allowed range due to line shorts or broken lines." 
        ::= { objectEntry 24623118 }
        
    rsBU10Failure                           OBJECT-TYPE 
        SYNTAX INTEGER  { normal(0),failure(1) } 
        ACCESS read-only 
        STATUS mandatory 
        DESCRIPTION 
            "This flag is set(1) when in bus unit 10
             a failure is detected." 
        ::= { objectEntry 24623119 }
        
    rsBU01ProgramFailureStored              OBJECT-TYPE 
        SYNTAX INTEGER  { off(0),stored(1) } 
        ACCESS read-only 
        STATUS mandatory 
        DESCRIPTION 
            "Stored flag: 'Bus unit 1, program failure'." 
        ::= { objectEntry 24623120 }
        
    rsBU01AgentLossStored                   OBJECT-TYPE 
        SYNTAX INTEGER  { off(0),stored(1) } 
        ACCESS read-only 
        STATUS mandatory 
        DESCRIPTION 
            "Stored flag: 'Bus unit 1, agent loss'." 
        ::= { objectEntry 24623121 }
        
    rsBU01SupplyVoltageLowStored            OBJECT-TYPE 
        SYNTAX INTEGER  { off(0),stored(1) } 
        ACCESS read-only 
        STATUS mandatory 
        DESCRIPTION 
            "Stored flag: 'Bus unit 1, supply voltage low'." 
        ::= { objectEntry 24623122 }
        
    rsBU01IgnitionVoltageLowStored          OBJECT-TYPE 
        SYNTAX INTEGER  { off(0),stored(1) } 
        ACCESS read-only 
        STATUS mandatory 
        DESCRIPTION 
            "Stored flag: 'Bus unit 1, ignition voltage low'." 
        ::= { objectEntry 24623123 }
        
    rsBU01CutOffLineFailureStored           OBJECT-TYPE 
        SYNTAX INTEGER  { off(0),stored(1) } 
        ACCESS read-only 
        STATUS mandatory 
        DESCRIPTION 
            "Stored flag: 'Bus unit 1, cut-off line failure'." 
        ::= { objectEntry 24623124 }
        
    rsBU01IgnitionLineFailureStored         OBJECT-TYPE 
        SYNTAX INTEGER  { off(0),stored(1) } 
        ACCESS read-only 
        STATUS mandatory 
        DESCRIPTION 
            "Stored flag: 'Bus unit 1, ignition line failure'." 
        ::= { objectEntry 24623125 }
        
    rsBU01ManActivationLineFailureStored    OBJECT-TYPE 
        SYNTAX INTEGER  { off(0),stored(1) } 
        ACCESS read-only 
        STATUS mandatory 
        DESCRIPTION 
            "Stored flag: 'Bus unit 1, manual activation line failure'." 
        ::= { objectEntry 24623126 }
        
    rsBU01FailureStored                     OBJECT-TYPE 
        SYNTAX INTEGER  { off(0),stored(1) } 
        ACCESS read-only 
        STATUS mandatory 
        DESCRIPTION 
            "Stored flag: 'Bus unit 1, failure'." 
        ::= { objectEntry 24623127 }
        
    rsBU02ProgramFailureStored              OBJECT-TYPE 
        SYNTAX INTEGER  { off(0),stored(1) } 
        ACCESS read-only 
        STATUS mandatory 
        DESCRIPTION 
            "Stored flag: 'Bus unit 2, program failure'." 
        ::= { objectEntry 24623128 }
        
    rsBU02AgentLossStored                   OBJECT-TYPE 
        SYNTAX INTEGER  { off(0),stored(1) } 
        ACCESS read-only 
        STATUS mandatory 
        DESCRIPTION 
            "Stored flag: 'Bus unit 2, agent loss'." 
        ::= { objectEntry 24623129 }
        
    rsBU02SupplyVoltageLowStored            OBJECT-TYPE 
        SYNTAX INTEGER  { off(0),stored(1) } 
        ACCESS read-only 
        STATUS mandatory 
        DESCRIPTION 
            "Stored flag: 'Bus unit 2, supply voltage low'." 
        ::= { objectEntry 24623130 }
        
    rsBU02IgnitionVoltageLowStored          OBJECT-TYPE 
        SYNTAX INTEGER  { off(0),stored(1) } 
        ACCESS read-only 
        STATUS mandatory 
        DESCRIPTION 
            "Stored flag: 'Bus unit 2, ignition voltage low'." 
        ::= { objectEntry 24623131 }
        
    rsBU02CutOffLineFailureStored           OBJECT-TYPE 
        SYNTAX INTEGER  { off(0),stored(1) } 
        ACCESS read-only 
        STATUS mandatory 
        DESCRIPTION 
            "Stored flag: 'Bus unit 2, cut-off line failure'." 
        ::= { objectEntry 24623132 }
        
    rsBU02IgnitionLineFailureStored         OBJECT-TYPE 
        SYNTAX INTEGER  { off(0),stored(1) } 
        ACCESS read-only 
        STATUS mandatory 
        DESCRIPTION 
            "Stored flag: 'Bus unit 2, ignition line failure'." 
        ::= { objectEntry 24623133 }
        
    rsBU02ManActivationLineFailureStored    OBJECT-TYPE 
        SYNTAX INTEGER  { off(0),stored(1) } 
        ACCESS read-only 
        STATUS mandatory 
        DESCRIPTION 
            "Stored flag: 'Bus unit 2, manual activation line failure'." 
        ::= { objectEntry 24623134 }
        
    rsBU02FailureStored                     OBJECT-TYPE 
        SYNTAX INTEGER  { off(0),stored(1) } 
        ACCESS read-only 
        STATUS mandatory 
        DESCRIPTION 
            "Stored flag: 'Bus unit 2, failure'." 
        ::= { objectEntry 24623135 }
        
    rsBU03ProgramFailureStored              OBJECT-TYPE 
        SYNTAX INTEGER  { off(0),stored(1) } 
        ACCESS read-only 
        STATUS mandatory 
        DESCRIPTION 
            "Stored flag: 'Bus unit 3, program failure'." 
        ::= { objectEntry 24623136 }
        
    rsBU03AgentLossStored                   OBJECT-TYPE 
        SYNTAX INTEGER  { off(0),stored(1) } 
        ACCESS read-only 
        STATUS mandatory 
        DESCRIPTION 
            "Stored flag: 'Bus unit 3, agent loss'." 
        ::= { objectEntry 24623137 }
        
    rsBU03SupplyVoltageLowStored            OBJECT-TYPE 
        SYNTAX INTEGER  { off(0),stored(1) } 
        ACCESS read-only 
        STATUS mandatory 
        DESCRIPTION 
            "Stored flag: 'Bus unit 3, supply voltage low'." 
        ::= { objectEntry 24623138 }
        
    rsBU03IgnitionVoltageLowStored          OBJECT-TYPE 
        SYNTAX INTEGER  { off(0),stored(1) } 
        ACCESS read-only 
        STATUS mandatory 
        DESCRIPTION 
            "Stored flag: 'Bus unit 3, ignition voltage low'." 
        ::= { objectEntry 24623139 }
        
    rsBU03CutOffLineFailureStored           OBJECT-TYPE 
        SYNTAX INTEGER  { off(0),stored(1) } 
        ACCESS read-only 
        STATUS mandatory 
        DESCRIPTION 
            "Stored flag: 'Bus unit 3, cut-off line failure'." 
        ::= { objectEntry 24623140 }
        
    rsBU03IgnitionLineFailureStored         OBJECT-TYPE 
        SYNTAX INTEGER  { off(0),stored(1) } 
        ACCESS read-only 
        STATUS mandatory 
        DESCRIPTION 
            "Stored flag: 'Bus unit 3, ignition line failure'." 
        ::= { objectEntry 24623141 }
        
    rsBU03ManActivationLineFailureStored    OBJECT-TYPE 
        SYNTAX INTEGER  { off(0),stored(1) } 
        ACCESS read-only 
        STATUS mandatory 
        DESCRIPTION 
            "Stored flag: 'Bus unit 3, manual activation line failure'." 
        ::= { objectEntry 24623142 }
        
    rsBU03FailureStored                     OBJECT-TYPE 
        SYNTAX INTEGER  { off(0),stored(1) } 
        ACCESS read-only 
        STATUS mandatory 
        DESCRIPTION 
            "Stored flag: 'Bus unit 3, failure'." 
        ::= { objectEntry 24623143 }
        
    rsBU04ProgramFailureStored              OBJECT-TYPE 
        SYNTAX INTEGER  { off(0),stored(1) } 
        ACCESS read-only 
        STATUS mandatory 
        DESCRIPTION 
            "Stored flag: 'Bus unit 4, program failure'." 
        ::= { objectEntry 24623144 }
        
    rsBU04AgentLossStored                   OBJECT-TYPE 
        SYNTAX INTEGER  { off(0),stored(1) } 
        ACCESS read-only 
        STATUS mandatory 
        DESCRIPTION 
            "Stored flag: 'Bus unit 4, agent loss'." 
        ::= { objectEntry 24623145 }
        
    rsBU04SupplyVoltageLowStored            OBJECT-TYPE 
        SYNTAX INTEGER  { off(0),stored(1) } 
        ACCESS read-only 
        STATUS mandatory 
        DESCRIPTION 
            "Stored flag: 'Bus unit 4, supply voltage low'." 
        ::= { objectEntry 24623146 }
        
    rsBU04IgnitionVoltageLowStored          OBJECT-TYPE 
        SYNTAX INTEGER  { off(0),stored(1) } 
        ACCESS read-only 
        STATUS mandatory 
        DESCRIPTION 
            "Stored flag: 'Bus unit 4, ignition voltage low'." 
        ::= { objectEntry 24623147 }
        
    rsBU04CutOffLineFailureStored           OBJECT-TYPE 
        SYNTAX INTEGER  { off(0),stored(1) } 
        ACCESS read-only 
        STATUS mandatory 
        DESCRIPTION 
            "Stored flag: 'Bus unit 4, cut-off line failure'." 
        ::= { objectEntry 24623148 }
        
    rsBU04IgnitionLineFailureStored         OBJECT-TYPE 
        SYNTAX INTEGER  { off(0),stored(1) } 
        ACCESS read-only 
        STATUS mandatory 
        DESCRIPTION 
            "Stored flag: 'Bus unit 4, ignition line failure'." 
        ::= { objectEntry 24623149 }
        
    rsBU04ManActivationLineFailureStored    OBJECT-TYPE 
        SYNTAX INTEGER  { off(0),stored(1) } 
        ACCESS read-only 
        STATUS mandatory 
        DESCRIPTION 
            "Stored flag: 'Bus unit 4, manual activation line failure'." 
        ::= { objectEntry 24623150 }
        
    rsBU04FailureStored                     OBJECT-TYPE 
        SYNTAX INTEGER  { off(0),stored(1) } 
        ACCESS read-only 
        STATUS mandatory 
        DESCRIPTION 
            "Stored flag: 'Bus unit 4, failure'." 
        ::= { objectEntry 24623151 }
        
    rsBU05ProgramFailureStored              OBJECT-TYPE 
        SYNTAX INTEGER  { off(0),stored(1) } 
        ACCESS read-only 
        STATUS mandatory 
        DESCRIPTION 
            "Stored flag: 'Bus unit 5, program failure'." 
        ::= { objectEntry 24623152 }
        
    rsBU05AgentLossStored                   OBJECT-TYPE 
        SYNTAX INTEGER  { off(0),stored(1) } 
        ACCESS read-only 
        STATUS mandatory 
        DESCRIPTION 
            "Stored flag: 'Bus unit 5, agent loss'." 
        ::= { objectEntry 24623153 }
        
    rsBU05SupplyVoltageLowStored            OBJECT-TYPE 
        SYNTAX INTEGER  { off(0),stored(1) } 
        ACCESS read-only 
        STATUS mandatory 
        DESCRIPTION 
            "Stored flag: 'Bus unit 5, supply voltage low'." 
        ::= { objectEntry 24623154 }
        
    rsBU05IgnitionVoltageLowStored          OBJECT-TYPE 
        SYNTAX INTEGER  { off(0),stored(1) } 
        ACCESS read-only 
        STATUS mandatory 
        DESCRIPTION 
            "Stored flag: 'Bus unit 5, ignition voltage low'." 
        ::= { objectEntry 24623155 }
        
    rsBU05CutOffLineFailureStored           OBJECT-TYPE 
        SYNTAX INTEGER  { off(0),stored(1) } 
        ACCESS read-only 
        STATUS mandatory 
        DESCRIPTION 
            "Stored flag: 'Bus unit 5, cut-off line failure'." 
        ::= { objectEntry 24623156 }
        
    rsBU05IgnitionLineFailureStored         OBJECT-TYPE 
        SYNTAX INTEGER  { off(0),stored(1) } 
        ACCESS read-only 
        STATUS mandatory 
        DESCRIPTION 
            "Stored flag: 'Bus unit 5, ignition line failure'." 
        ::= { objectEntry 24623157 }
        
    rsBU05ManActivationLineFailureStored    OBJECT-TYPE 
        SYNTAX INTEGER  { off(0),stored(1) } 
        ACCESS read-only 
        STATUS mandatory 
        DESCRIPTION 
            "Stored flag: 'Bus unit 5, manual activation line failure'." 
        ::= { objectEntry 24623158 }
        
    rsBU05FailureStored                     OBJECT-TYPE 
        SYNTAX INTEGER  { off(0),stored(1) } 
        ACCESS read-only 
        STATUS mandatory 
        DESCRIPTION 
            "Stored flag: 'Bus unit 5, failure'." 
        ::= { objectEntry 24623159 }
        
    rsBU06ProgramFailureStored              OBJECT-TYPE 
        SYNTAX INTEGER  { off(0),stored(1) } 
        ACCESS read-only 
        STATUS mandatory 
        DESCRIPTION 
            "Stored flag: 'Bus unit 6, program failure'." 
        ::= { objectEntry 24623160 }
        
    rsBU06AgentLossStored                   OBJECT-TYPE 
        SYNTAX INTEGER  { off(0),stored(1) } 
        ACCESS read-only 
        STATUS mandatory 
        DESCRIPTION 
            "Stored flag: 'Bus unit 6, agent loss'." 
        ::= { objectEntry 24623161 }
        
    rsBU06SupplyVoltageLowStored            OBJECT-TYPE 
        SYNTAX INTEGER  { off(0),stored(1) } 
        ACCESS read-only 
        STATUS mandatory 
        DESCRIPTION 
            "Stored flag: 'Bus unit 6, supply voltage low'." 
        ::= { objectEntry 24623162 }
        
    rsBU06IgnitionVoltageLowStored          OBJECT-TYPE 
        SYNTAX INTEGER  { off(0),stored(1) } 
        ACCESS read-only 
        STATUS mandatory 
        DESCRIPTION 
            "Stored flag: 'Bus unit 6, ignition voltage low'." 
        ::= { objectEntry 24623163 }
        
    rsBU06CutOffLineFailureStored           OBJECT-TYPE 
        SYNTAX INTEGER  { off(0),stored(1) } 
        ACCESS read-only 
        STATUS mandatory 
        DESCRIPTION 
            "Stored flag: 'Bus unit 6, cut-off line failure'." 
        ::= { objectEntry 24623164 }
        
    rsBU06IgnitionLineFailureStored         OBJECT-TYPE 
        SYNTAX INTEGER  { off(0),stored(1) } 
        ACCESS read-only 
        STATUS mandatory 
        DESCRIPTION 
            "Stored flag: 'Bus unit 6, ignition line failure'." 
        ::= { objectEntry 24623165 }
        
    rsBU06ManActivationLineFailureStored    OBJECT-TYPE 
        SYNTAX INTEGER  { off(0),stored(1) } 
        ACCESS read-only 
        STATUS mandatory 
        DESCRIPTION 
            "Stored flag: 'Bus unit 6, manual activation line failure'." 
        ::= { objectEntry 24623166 }
        
    rsBU06FailureStored                     OBJECT-TYPE 
        SYNTAX INTEGER  { off(0),stored(1) } 
        ACCESS read-only 
        STATUS mandatory 
        DESCRIPTION 
            "Stored flag: 'Bus unit 6, failure'." 
        ::= { objectEntry 24623167 }
        
    rsBU07ProgramFailureStored              OBJECT-TYPE 
        SYNTAX INTEGER  { off(0),stored(1) } 
        ACCESS read-only 
        STATUS mandatory 
        DESCRIPTION 
            "Stored flag: 'Bus unit 7, program failure'." 
        ::= { objectEntry 24623168 }
        
    rsBU07AgentLossStored                   OBJECT-TYPE 
        SYNTAX INTEGER  { off(0),stored(1) } 
        ACCESS read-only 
        STATUS mandatory 
        DESCRIPTION 
            "Stored flag: 'Bus unit 7, agent loss'." 
        ::= { objectEntry 24623169 }
        
    rsBU07SupplyVoltageLowStored            OBJECT-TYPE 
        SYNTAX INTEGER  { off(0),stored(1) } 
        ACCESS read-only 
        STATUS mandatory 
        DESCRIPTION 
            "Stored flag: 'Bus unit 7, supply voltage low'." 
        ::= { objectEntry 24623170 }
        
    rsBU07IgnitionVoltageLowStored          OBJECT-TYPE 
        SYNTAX INTEGER  { off(0),stored(1) } 
        ACCESS read-only 
        STATUS mandatory 
        DESCRIPTION 
            "Stored flag: 'Bus unit 7, ignition voltage low'." 
        ::= { objectEntry 24623171 }
        
    rsBU07CutOffLineFailureStored           OBJECT-TYPE 
        SYNTAX INTEGER  { off(0),stored(1) } 
        ACCESS read-only 
        STATUS mandatory 
        DESCRIPTION 
            "Stored flag: 'Bus unit 7, cut-off line failure'." 
        ::= { objectEntry 24623172 }
        
    rsBU07IgnitionLineFailureStored         OBJECT-TYPE 
        SYNTAX INTEGER  { off(0),stored(1) } 
        ACCESS read-only 
        STATUS mandatory 
        DESCRIPTION 
            "Stored flag: 'Bus unit 7, ignition line failure'." 
        ::= { objectEntry 24623173 }
        
    rsBU07ManActivationLineFailureStored    OBJECT-TYPE 
        SYNTAX INTEGER  { off(0),stored(1) } 
        ACCESS read-only 
        STATUS mandatory 
        DESCRIPTION 
            "Stored flag: 'Bus unit 7, manual activation line failure'." 
        ::= { objectEntry 24623174 }
        
    rsBU07FailureStored                     OBJECT-TYPE 
        SYNTAX INTEGER  { off(0),stored(1) } 
        ACCESS read-only 
        STATUS mandatory 
        DESCRIPTION 
            "Stored flag: 'Bus unit 7, failure'." 
        ::= { objectEntry 24623175 }
        
    rsBU08ProgramFailureStored              OBJECT-TYPE 
        SYNTAX INTEGER  { off(0),stored(1) } 
        ACCESS read-only 
        STATUS mandatory 
        DESCRIPTION 
            "Stored flag: 'Bus unit 8, program failure'." 
        ::= { objectEntry 24623176 }
        
    rsBU08AgentLossStored                   OBJECT-TYPE 
        SYNTAX INTEGER  { off(0),stored(1) } 
        ACCESS read-only 
        STATUS mandatory 
        DESCRIPTION 
            "Stored flag: 'Bus unit 8, agent loss'." 
        ::= { objectEntry 24623177 }
        
    rsBU08SupplyVoltageLowStored            OBJECT-TYPE 
        SYNTAX INTEGER  { off(0),stored(1) } 
        ACCESS read-only 
        STATUS mandatory 
        DESCRIPTION 
            "Stored flag: 'Bus unit 8, supply voltage low'." 
        ::= { objectEntry 24623178 }
        
    rsBU08IgnitionVoltageLowStored          OBJECT-TYPE 
        SYNTAX INTEGER  { off(0),stored(1) } 
        ACCESS read-only 
        STATUS mandatory 
        DESCRIPTION 
            "Stored flag: 'Bus unit 8, ignition voltage low'." 
        ::= { objectEntry 24623179 }
        
    rsBU08CutOffLineFailureStored           OBJECT-TYPE 
        SYNTAX INTEGER  { off(0),stored(1) } 
        ACCESS read-only 
        STATUS mandatory 
        DESCRIPTION 
            "Stored flag: 'Bus unit 8, cut-off line failure'." 
        ::= { objectEntry 24623180 }
        
    rsBU08IgnitionLineFailureStored         OBJECT-TYPE 
        SYNTAX INTEGER  { off(0),stored(1) } 
        ACCESS read-only 
        STATUS mandatory 
        DESCRIPTION 
            "Stored flag: 'Bus unit 8, ignition line failure'." 
        ::= { objectEntry 24623181 }
        
    rsBU08ManActivationLineFailureStored    OBJECT-TYPE 
        SYNTAX INTEGER  { off(0),stored(1) } 
        ACCESS read-only 
        STATUS mandatory 
        DESCRIPTION 
            "Stored flag: 'Bus unit 8, manual activation line failure'." 
        ::= { objectEntry 24623182 }
        
    rsBU08FailureStored                     OBJECT-TYPE 
        SYNTAX INTEGER  { off(0),stored(1) } 
        ACCESS read-only 
        STATUS mandatory 
        DESCRIPTION 
            "Stored flag: 'Bus unit 8, failure'." 
        ::= { objectEntry 24623183 }
        
    rsBU09ProgramFailureStored              OBJECT-TYPE 
        SYNTAX INTEGER  { off(0),stored(1) } 
        ACCESS read-only 
        STATUS mandatory 
        DESCRIPTION 
            "Stored flag: 'Bus unit 9, program failure'." 
        ::= { objectEntry 24623184 }
        
    rsBU09AgentLossStored                   OBJECT-TYPE 
        SYNTAX INTEGER  { off(0),stored(1) } 
        ACCESS read-only 
        STATUS mandatory 
        DESCRIPTION 
            "Stored flag: 'Bus unit 9, agent loss'." 
        ::= { objectEntry 24623185 }
        
    rsBU09SupplyVoltageLowStored            OBJECT-TYPE 
        SYNTAX INTEGER  { off(0),stored(1) } 
        ACCESS read-only 
        STATUS mandatory 
        DESCRIPTION 
            "Stored flag: 'Bus unit 9, supply voltage low'." 
        ::= { objectEntry 24623186 }
        
    rsBU09IgnitionVoltageLowStored          OBJECT-TYPE 
        SYNTAX INTEGER  { off(0),stored(1) } 
        ACCESS read-only 
        STATUS mandatory 
        DESCRIPTION 
            "Stored flag: 'Bus unit 9, ignition voltage low'." 
        ::= { objectEntry 24623187 }
        
    rsBU09CutOffLineFailureStored           OBJECT-TYPE 
        SYNTAX INTEGER  { off(0),stored(1) } 
        ACCESS read-only 
        STATUS mandatory 
        DESCRIPTION 
            "Stored flag: 'Bus unit 9, cut-off line failure'." 
        ::= { objectEntry 24623188 }
        
    rsBU09IgnitionLineFailureStored         OBJECT-TYPE 
        SYNTAX INTEGER  { off(0),stored(1) } 
        ACCESS read-only 
        STATUS mandatory 
        DESCRIPTION 
            "Stored flag: 'Bus unit 9, ignition line failure'." 
        ::= { objectEntry 24623189 }
        
    rsBU09ManActivationLineFailureStored    OBJECT-TYPE 
        SYNTAX INTEGER  { off(0),stored(1) } 
        ACCESS read-only 
        STATUS mandatory 
        DESCRIPTION 
            "Stored flag: 'Bus unit 9, manual activation line failure'." 
        ::= { objectEntry 24623190 }
        
    rsBU09FailureStored                     OBJECT-TYPE 
        SYNTAX INTEGER  { off(0),stored(1) } 
        ACCESS read-only 
        STATUS mandatory 
        DESCRIPTION 
            "Stored flag: 'Bus unit 9, failure'." 
        ::= { objectEntry 24623191 }
        
    rsBU10ProgramFailureStored              OBJECT-TYPE 
        SYNTAX INTEGER  { off(0),stored(1) } 
        ACCESS read-only 
        STATUS mandatory 
        DESCRIPTION 
            "Stored flag: 'Bus unit 10, program failure'." 
        ::= { objectEntry 24623192 }
        
    rsBU10AgentLossStored                   OBJECT-TYPE 
        SYNTAX INTEGER  { off(0),stored(1) } 
        ACCESS read-only 
        STATUS mandatory 
        DESCRIPTION 
            "Stored flag: 'Bus unit 10, agent loss'." 
        ::= { objectEntry 24623193 }
        
    rsBU10SupplyVoltageLowStored            OBJECT-TYPE 
        SYNTAX INTEGER  { off(0),stored(1) } 
        ACCESS read-only 
        STATUS mandatory 
        DESCRIPTION 
            "Stored flag: 'Bus unit 10, supply voltage low'." 
        ::= { objectEntry 24623194 }
        
    rsBU10IgnitionVoltageLowStored          OBJECT-TYPE 
        SYNTAX INTEGER  { off(0),stored(1) } 
        ACCESS read-only 
        STATUS mandatory 
        DESCRIPTION 
            "Stored flag: 'Bus unit 10, ignition voltage low'." 
        ::= { objectEntry 24623195 }
        
    rsBU10CutOffLineFailureStored           OBJECT-TYPE 
        SYNTAX INTEGER  { off(0),stored(1) } 
        ACCESS read-only 
        STATUS mandatory 
        DESCRIPTION 
            "Stored flag: 'Bus unit 10, cut-off line failure'." 
        ::= { objectEntry 24623196 }
        
    rsBU10IgnitionLineFailureStored         OBJECT-TYPE 
        SYNTAX INTEGER  { off(0),stored(1) } 
        ACCESS read-only 
        STATUS mandatory 
        DESCRIPTION 
            "Stored flag: 'Bus unit 10, ignition line failure'." 
        ::= { objectEntry 24623197 }
        
    rsBU10ManActivationLineFailureStored    OBJECT-TYPE 
        SYNTAX INTEGER  { off(0),stored(1) } 
        ACCESS read-only 
        STATUS mandatory 
        DESCRIPTION 
            "Stored flag: 'Bus unit 10, manual activation line failure'." 
        ::= { objectEntry 24623198 }
        
    rsBU10FailureStored                     OBJECT-TYPE 
        SYNTAX INTEGER  { off(0),stored(1) } 
        ACCESS read-only 
        STATUS mandatory 
        DESCRIPTION 
            "Stored flag: 'Bus unit 10, failure'." 
        ::= { objectEntry 24623199 }
        
    ----------------------------------------------------
    -- Bits from RackSens data object 24624 (6030 hex)
    ----------------------------------------------------

    rsBU01ActivatedDisplayBlinking          OBJECT-TYPE 
        SYNTAX INTEGER  { off(0),blinking(1) } 
        ACCESS read-only 
        STATUS mandatory 
        DESCRIPTION 
            "If set(1) the 'activated' display 
             on bus unit 1 is blinking." 
        ::= { objectEntry 24624000 }
        
    rsBU01ActivatedDisplayOn                OBJECT-TYPE 
        SYNTAX INTEGER  { off(0),on(1)} 
        ACCESS read-only 
        STATUS mandatory 
        DESCRIPTION 
            "If set(1) the 'activated' display
             on bus unit 1  is steady on." 
        ::= { objectEntry 24624001 }
        
    rsBU01ServiceDisplayBlinking            OBJECT-TYPE 
        SYNTAX INTEGER  { off(0),blinking(1) } 
        ACCESS read-only 
        STATUS mandatory 
        DESCRIPTION 
            "If set(1) the 'service / blocked' display 
             on bus unit 1 is blinking." 
        ::= { objectEntry 24624002 }
        
    rsBU01ServiceDisplayOn                  OBJECT-TYPE 
        SYNTAX INTEGER  { off(0),on(1)} 
        ACCESS read-only 
        STATUS mandatory 
        DESCRIPTION 
            "If set(1) the 'service / blocked' display 
             on bus unit 1  is steady on." 
        ::= { objectEntry 24624003 }
        
    rsBU01FailureDisplayBlinking            OBJECT-TYPE 
        SYNTAX INTEGER  { off(0),blinking(1) } 
        ACCESS read-only 
        STATUS mandatory 
        DESCRIPTION 
            "If set(1) the 'failure' display 
             on bus unit 1 is blinking." 
        ::= { objectEntry 24624004 }
        
    rsBU01FailureDisplayOn                  OBJECT-TYPE 
        SYNTAX INTEGER  { off(0),on(1)} 
        ACCESS read-only 
        STATUS mandatory 
        DESCRIPTION 
            "If set(1) the 'failure' display 
             on bus unit 1  is steady on." 
        ::= { objectEntry 24624005 }
        
    rsBU01OperatingDisplayBlinking          OBJECT-TYPE 
        SYNTAX INTEGER  { off(0),blinking(1) } 
        ACCESS read-only 
        STATUS mandatory 
        DESCRIPTION 
            "If set(1) the 'operating' display 
             on bus unit 1 is blinking." 
        ::= { objectEntry 24624006 }
        
    rsBU01OperatingDisplayOn                OBJECT-TYPE 
        SYNTAX INTEGER  { off(0),on(1)} 
        ACCESS read-only 
        STATUS mandatory 
        DESCRIPTION 
            "If set(1) the 'operating' display 
             on bus unit 1  is steady on." 
        ::= { objectEntry 24624007 }
        
    rsBU01ManualActivationDisplayBlinking   OBJECT-TYPE 
        SYNTAX INTEGER  { off(0),blinking(1) } 
        ACCESS read-only 
        STATUS mandatory 
        DESCRIPTION 
            "If set(1) the 'manual activation' display 
             on bus unit 1 is blinking." 
        ::= { objectEntry 24624008 }
        
    rsBU01ManualActivationDisplayOn         OBJECT-TYPE 
        SYNTAX INTEGER  { off(0),on(1)} 
        ACCESS read-only 
        STATUS mandatory 
        DESCRIPTION 
            "If set(1) the 'manual activation' display 
             on bus unit 1  is steady on." 
        ::= { objectEntry 24624009 }
        
    rsBU01OnlineDisplayDisplayOn            OBJECT-TYPE 
        SYNTAX INTEGER  { off(0),on(1)} 
        ACCESS read-only 
        STATUS mandatory 
        DESCRIPTION 
            "If set(1) the 'online' display 
             on bus unit 1  is steady on." 
        ::= { objectEntry 24624010 }
        
    rsBU01IgnitionLineActivatedDisplayOn    OBJECT-TYPE 
        SYNTAX INTEGER  { off(0),on(1)} 
        ACCESS read-only 
        STATUS mandatory 
        DESCRIPTION 
            "If set(1) the 'ignition line activated' display 
             on bus unit 1  is steady on." 
        ::= { objectEntry 24624011 }
        
    rsBU01CutOffLineActivatedDisplayOn      OBJECT-TYPE 
        SYNTAX INTEGER  { off(0),on(1)} 
        ACCESS read-only 
        STATUS mandatory 
        DESCRIPTION 
            "If set(1) the 'cut-off line activated' display 
             on bus unit 1  is steady on." 
        ::= { objectEntry 24624012 }
        
    rsBU01DoorSwitchDisplayOn               OBJECT-TYPE 
        SYNTAX INTEGER  { off(0),on(1)} 
        ACCESS read-only 
        STATUS mandatory 
        DESCRIPTION 
            "If set(1) the 'door switch' display 
             on bus unit 1  is steady on." 
        ::= { objectEntry 24624013 }
        
    rsBU01Bit14                             OBJECT-TYPE 
        SYNTAX INTEGER  { off(0),on(1)} 
        ACCESS read-only 
        STATUS mandatory 
        DESCRIPTION 
            "Unused bit." 
        ::= { objectEntry 24624014 }
        
    rsBU01Bit15                             OBJECT-TYPE 
        SYNTAX INTEGER  { off(0),on(1)} 
        ACCESS read-only 
        STATUS mandatory 
        DESCRIPTION 
            "Unused bit." 
        ::= { objectEntry 24624015 }
        
    rsBU02ActivatedDisplayBlinking          OBJECT-TYPE 
        SYNTAX INTEGER  { off(0),blinking(1) } 
        ACCESS read-only 
        STATUS mandatory 
        DESCRIPTION 
            "If set(1) the 'activated' display 
             on bus unit 2 is blinking." 
        ::= { objectEntry 24624016 }
        
    rsBU02ActivatedDisplayOn                OBJECT-TYPE 
        SYNTAX INTEGER  { off(0),on(1)} 
        ACCESS read-only 
        STATUS mandatory 
        DESCRIPTION 
            "If set(1) the 'activated' display
             on bus unit 2  is steady on." 
        ::= { objectEntry 24624017 }
        
    rsBU02ServiceDisplayBlinking            OBJECT-TYPE 
        SYNTAX INTEGER  { off(0),blinking(1) } 
        ACCESS read-only 
        STATUS mandatory 
        DESCRIPTION 
            "If set(1) the 'service / blocked' display 
             on bus unit 2 is blinking." 
        ::= { objectEntry 24624018 }
        
    rsBU02ServiceDisplayOn                  OBJECT-TYPE 
        SYNTAX INTEGER  { off(0),on(1)} 
        ACCESS read-only 
        STATUS mandatory 
        DESCRIPTION 
            "If set(1) the 'service / blocked' display 
             on bus unit 2  is steady on." 
        ::= { objectEntry 24624019 }
        
    rsBU02FailureDisplayBlinking            OBJECT-TYPE 
        SYNTAX INTEGER  { off(0),blinking(1) } 
        ACCESS read-only 
        STATUS mandatory 
        DESCRIPTION 
            "If set(1) the 'failure' display 
             on bus unit 2 is blinking." 
        ::= { objectEntry 24624020 }
        
    rsBU02FailureDisplayOn                  OBJECT-TYPE 
        SYNTAX INTEGER  { off(0),on(1)} 
        ACCESS read-only 
        STATUS mandatory 
        DESCRIPTION 
            "If set(1) the 'failure' display 
             on bus unit 2  is steady on." 
        ::= { objectEntry 24624021 }
        
    rsBU02OperatingDisplayBlinking          OBJECT-TYPE 
        SYNTAX INTEGER  { off(0),blinking(1) } 
        ACCESS read-only 
        STATUS mandatory 
        DESCRIPTION 
            "If set(1) the 'operating' display 
             on bus unit 2 is blinking." 
        ::= { objectEntry 24624022 }
        
    rsBU02OperatingDisplayOn                OBJECT-TYPE 
        SYNTAX INTEGER  { off(0),on(1)} 
        ACCESS read-only 
        STATUS mandatory 
        DESCRIPTION 
            "If set(1) the 'operating' display 
             on bus unit 2  is steady on." 
        ::= { objectEntry 24624023 }
        
    rsBU02ManualActivationDisplayBlinking   OBJECT-TYPE 
        SYNTAX INTEGER  { off(0),blinking(1) } 
        ACCESS read-only 
        STATUS mandatory 
        DESCRIPTION 
            "If set(1) the 'manual activation' display 
             on bus unit 2 is blinking." 
        ::= { objectEntry 24624024 }
        
    rsBU02ManualActivationDisplayOn         OBJECT-TYPE 
        SYNTAX INTEGER  { off(0),on(1)} 
        ACCESS read-only 
        STATUS mandatory 
        DESCRIPTION 
            "If set(1) the 'manual activation' display 
             on bus unit 2  is steady on." 
        ::= { objectEntry 24624025 }
        
    rsBU02OnlineDisplayDisplayOn            OBJECT-TYPE 
        SYNTAX INTEGER  { off(0),on(1)} 
        ACCESS read-only 
        STATUS mandatory 
        DESCRIPTION 
            "If set(1) the 'online' display 
             on bus unit 2  is steady on." 
        ::= { objectEntry 24624026 }
        
    rsBU02IgnitionLineActivatedDisplayOn    OBJECT-TYPE 
        SYNTAX INTEGER  { off(0),on(1)} 
        ACCESS read-only 
        STATUS mandatory 
        DESCRIPTION 
            "If set(1) the 'ignition line activated' display 
             on bus unit 2  is steady on." 
        ::= { objectEntry 24624027 }
        
    rsBU02CutOffLineActivatedDisplayOn      OBJECT-TYPE 
        SYNTAX INTEGER  { off(0),on(1)} 
        ACCESS read-only 
        STATUS mandatory 
        DESCRIPTION 
            "If set(1) the 'cut-off line activated' display 
             on bus unit 2  is steady on." 
        ::= { objectEntry 24624028 }
        
    rsBU02DoorSwitchDisplayOn               OBJECT-TYPE 
        SYNTAX INTEGER  { off(0),on(1)} 
        ACCESS read-only 
        STATUS mandatory 
        DESCRIPTION 
            "If set(1) the 'door switch' display 
             on bus unit 2  is steady on." 
        ::= { objectEntry 24624029 }
        
    rsBU02Bit14                             OBJECT-TYPE 
        SYNTAX INTEGER  { off(0),on(1)} 
        ACCESS read-only 
        STATUS mandatory 
        DESCRIPTION 
            "Unused bit." 
        ::= { objectEntry 24624030 }
        
    rsBU02Bit15                             OBJECT-TYPE 
        SYNTAX INTEGER  { off(0),on(1)} 
        ACCESS read-only 
        STATUS mandatory 
        DESCRIPTION 
            "Unused bit." 
        ::= { objectEntry 24624031 }
        
    rsBU03ActivatedDisplayBlinking          OBJECT-TYPE 
        SYNTAX INTEGER  { off(0),blinking(1) } 
        ACCESS read-only 
        STATUS mandatory 
        DESCRIPTION 
            "If set(1) the 'activated' display 
             on bus unit 3 is blinking." 
        ::= { objectEntry 24624032 }
        
    rsBU03ActivatedDisplayOn                OBJECT-TYPE 
        SYNTAX INTEGER  { off(0),on(1)} 
        ACCESS read-only 
        STATUS mandatory 
        DESCRIPTION 
            "If set(1) the 'activated' display
             on bus unit 3  is steady on." 
        ::= { objectEntry 24624033 }
        
    rsBU03ServiceDisplayBlinking            OBJECT-TYPE 
        SYNTAX INTEGER  { off(0),blinking(1) } 
        ACCESS read-only 
        STATUS mandatory 
        DESCRIPTION 
            "If set(1) the 'service / blocked' display 
             on bus unit 3 is blinking." 
        ::= { objectEntry 24624034 }
        
    rsBU03ServiceDisplayOn                  OBJECT-TYPE 
        SYNTAX INTEGER  { off(0),on(1)} 
        ACCESS read-only 
        STATUS mandatory 
        DESCRIPTION 
            "If set(1) the 'service / blocked' display 
             on bus unit 3  is steady on." 
        ::= { objectEntry 24624035 }
        
    rsBU03FailureDisplayBlinking            OBJECT-TYPE 
        SYNTAX INTEGER  { off(0),blinking(1) } 
        ACCESS read-only 
        STATUS mandatory 
        DESCRIPTION 
            "If set(1) the 'failure' display 
             on bus unit 3 is blinking." 
        ::= { objectEntry 24624036 }
        
    rsBU03FailureDisplayOn                  OBJECT-TYPE 
        SYNTAX INTEGER  { off(0),on(1)} 
        ACCESS read-only 
        STATUS mandatory 
        DESCRIPTION 
            "If set(1) the 'failure' display 
             on bus unit 3  is steady on." 
        ::= { objectEntry 24624037 }
        
    rsBU03OperatingDisplayBlinking          OBJECT-TYPE 
        SYNTAX INTEGER  { off(0),blinking(1) } 
        ACCESS read-only 
        STATUS mandatory 
        DESCRIPTION 
            "If set(1) the 'operating' display 
             on bus unit 3 is blinking." 
        ::= { objectEntry 24624038 }
        
    rsBU03OperatingDisplayOn                OBJECT-TYPE 
        SYNTAX INTEGER  { off(0),on(1)} 
        ACCESS read-only 
        STATUS mandatory 
        DESCRIPTION 
            "If set(1) the 'operating' display 
             on bus unit 3  is steady on." 
        ::= { objectEntry 24624039 }
        
    rsBU03ManualActivationDisplayBlinking   OBJECT-TYPE 
        SYNTAX INTEGER  { off(0),blinking(1) } 
        ACCESS read-only 
        STATUS mandatory 
        DESCRIPTION 
            "If set(1) the 'manual activation' display 
             on bus unit 3 is blinking." 
        ::= { objectEntry 24624040 }
        
    rsBU03ManualActivationDisplayOn         OBJECT-TYPE 
        SYNTAX INTEGER  { off(0),on(1)} 
        ACCESS read-only 
        STATUS mandatory 
        DESCRIPTION 
            "If set(1) the 'manual activation' display 
             on bus unit 3  is steady on." 
        ::= { objectEntry 24624041 }
        
    rsBU03OnlineDisplayDisplayOn            OBJECT-TYPE 
        SYNTAX INTEGER  { off(0),on(1)} 
        ACCESS read-only 
        STATUS mandatory 
        DESCRIPTION 
            "If set(1) the 'online' display 
             on bus unit 3  is steady on." 
        ::= { objectEntry 24624042 }
        
    rsBU03IgnitionLineActivatedDisplayOn    OBJECT-TYPE 
        SYNTAX INTEGER  { off(0),on(1)} 
        ACCESS read-only 
        STATUS mandatory 
        DESCRIPTION 
            "If set(1) the 'ignition line activated' display 
             on bus unit 3  is steady on." 
        ::= { objectEntry 24624043 }
        
    rsBU03CutOffLineActivatedDisplayOn      OBJECT-TYPE 
        SYNTAX INTEGER  { off(0),on(1)} 
        ACCESS read-only 
        STATUS mandatory 
        DESCRIPTION 
            "If set(1) the 'cut-off line activated' display 
             on bus unit 3  is steady on." 
        ::= { objectEntry 24624044 }
        
    rsBU03DoorSwitchDisplayOn               OBJECT-TYPE 
        SYNTAX INTEGER  { off(0),on(1)} 
        ACCESS read-only 
        STATUS mandatory 
        DESCRIPTION 
            "If set(1) the 'door switch' display 
             on bus unit 3  is steady on." 
        ::= { objectEntry 24624045 }
        
    rsBU03Bit14                             OBJECT-TYPE 
        SYNTAX INTEGER  { off(0),on(1)} 
        ACCESS read-only 
        STATUS mandatory 
        DESCRIPTION 
            "Unused bit." 
        ::= { objectEntry 24624046 }
        
    rsBU03Bit15                             OBJECT-TYPE 
        SYNTAX INTEGER  { off(0),on(1)} 
        ACCESS read-only 
        STATUS mandatory 
        DESCRIPTION 
            "Unused bit." 
        ::= { objectEntry 24624047 }
        
    rsBU04ActivatedDisplayBlinking          OBJECT-TYPE 
        SYNTAX INTEGER  { off(0),blinking(1) } 
        ACCESS read-only 
        STATUS mandatory 
        DESCRIPTION 
            "If set(1) the 'activated' display 
             on bus unit 4 is blinking." 
        ::= { objectEntry 24624048 }
        
    rsBU04ActivatedDisplayOn                OBJECT-TYPE 
        SYNTAX INTEGER  { off(0),on(1)} 
        ACCESS read-only 
        STATUS mandatory 
        DESCRIPTION 
            "If set(1) the 'activated' display
             on bus unit 4  is steady on." 
        ::= { objectEntry 24624049 }
        
    rsBU04ServiceDisplayBlinking            OBJECT-TYPE 
        SYNTAX INTEGER  { off(0),blinking(1) } 
        ACCESS read-only 
        STATUS mandatory 
        DESCRIPTION 
            "If set(1) the 'service / blocked' display 
             on bus unit 4 is blinking." 
        ::= { objectEntry 24624050 }
        
    rsBU04ServiceDisplayOn                  OBJECT-TYPE 
        SYNTAX INTEGER  { off(0),on(1)} 
        ACCESS read-only 
        STATUS mandatory 
        DESCRIPTION 
            "If set(1) the 'service / blocked' display 
             on bus unit 4  is steady on." 
        ::= { objectEntry 24624051 }
        
    rsBU04FailureDisplayBlinking            OBJECT-TYPE 
        SYNTAX INTEGER  { off(0),blinking(1) } 
        ACCESS read-only 
        STATUS mandatory 
        DESCRIPTION 
            "If set(1) the 'failure' display 
             on bus unit 4 is blinking." 
        ::= { objectEntry 24624052 }
        
    rsBU04FailureDisplayOn                  OBJECT-TYPE 
        SYNTAX INTEGER  { off(0),on(1)} 
        ACCESS read-only 
        STATUS mandatory 
        DESCRIPTION 
            "If set(1) the 'failure' display 
             on bus unit 4  is steady on." 
        ::= { objectEntry 24624053 }
        
    rsBU04OperatingDisplayBlinking          OBJECT-TYPE 
        SYNTAX INTEGER  { off(0),blinking(1) } 
        ACCESS read-only 
        STATUS mandatory 
        DESCRIPTION 
            "If set(1) the 'operating' display 
             on bus unit 4 is blinking." 
        ::= { objectEntry 24624054 }
        
    rsBU04OperatingDisplayOn                OBJECT-TYPE 
        SYNTAX INTEGER  { off(0),on(1)} 
        ACCESS read-only 
        STATUS mandatory 
        DESCRIPTION 
            "If set(1) the 'operating' display 
             on bus unit 4  is steady on." 
        ::= { objectEntry 24624055 }
        
    rsBU04ManualActivationDisplayBlinking   OBJECT-TYPE 
        SYNTAX INTEGER  { off(0),blinking(1) } 
        ACCESS read-only 
        STATUS mandatory 
        DESCRIPTION 
            "If set(1) the 'manual activation' display 
             on bus unit 4 is blinking." 
        ::= { objectEntry 24624056 }
        
    rsBU04ManualActivationDisplayOn         OBJECT-TYPE 
        SYNTAX INTEGER  { off(0),on(1)} 
        ACCESS read-only 
        STATUS mandatory 
        DESCRIPTION 
            "If set(1) the 'manual activation' display 
             on bus unit 4  is steady on." 
        ::= { objectEntry 24624057 }
        
    rsBU04OnlineDisplayDisplayOn            OBJECT-TYPE 
        SYNTAX INTEGER  { off(0),on(1)} 
        ACCESS read-only 
        STATUS mandatory 
        DESCRIPTION 
            "If set(1) the 'online' display 
             on bus unit 4  is steady on." 
        ::= { objectEntry 24624058 }
        
    rsBU04IgnitionLineActivatedDisplayOn    OBJECT-TYPE 
        SYNTAX INTEGER  { off(0),on(1)} 
        ACCESS read-only 
        STATUS mandatory 
        DESCRIPTION 
            "If set(1) the 'ignition line activated' display 
             on bus unit 4  is steady on." 
        ::= { objectEntry 24624059 }
        
    rsBU04CutOffLineActivatedDisplayOn      OBJECT-TYPE 
        SYNTAX INTEGER  { off(0),on(1)} 
        ACCESS read-only 
        STATUS mandatory 
        DESCRIPTION 
            "If set(1) the 'cut-off line activated' display 
             on bus unit 4  is steady on." 
        ::= { objectEntry 24624060 }
        
    rsBU04DoorSwitchDisplayOn               OBJECT-TYPE 
        SYNTAX INTEGER  { off(0),on(1)} 
        ACCESS read-only 
        STATUS mandatory 
        DESCRIPTION 
            "If set(1) the 'door switch' display 
             on bus unit 4  is steady on." 
        ::= { objectEntry 24624061 }
        
    rsBU04Bit14                             OBJECT-TYPE 
        SYNTAX INTEGER  { off(0),on(1)} 
        ACCESS read-only 
        STATUS mandatory 
        DESCRIPTION 
            "Unused bit." 
        ::= { objectEntry 24624062 }
        
    rsBU04Bit15                             OBJECT-TYPE 
        SYNTAX INTEGER  { off(0),on(1)} 
        ACCESS read-only 
        STATUS mandatory 
        DESCRIPTION 
            "Unused bit." 
        ::= { objectEntry 24624063 }
        
    rsBU05ActivatedDisplayBlinking          OBJECT-TYPE 
        SYNTAX INTEGER  { off(0),blinking(1) } 
        ACCESS read-only 
        STATUS mandatory 
        DESCRIPTION 
            "If set(1) the 'activated' display 
             on bus unit 5 is blinking." 
        ::= { objectEntry 24624064 }
        
    rsBU05ActivatedDisplayOn                OBJECT-TYPE 
        SYNTAX INTEGER  { off(0),on(1)} 
        ACCESS read-only 
        STATUS mandatory 
        DESCRIPTION 
            "If set(1) the 'activated' display
             on bus unit 5  is steady on." 
        ::= { objectEntry 24624065 }
        
    rsBU05ServiceDisplayBlinking            OBJECT-TYPE 
        SYNTAX INTEGER  { off(0),blinking(1) } 
        ACCESS read-only 
        STATUS mandatory 
        DESCRIPTION 
            "If set(1) the 'service / blocked' display 
             on bus unit 5 is blinking." 
        ::= { objectEntry 24624066 }
        
    rsBU05ServiceDisplayOn                  OBJECT-TYPE 
        SYNTAX INTEGER  { off(0),on(1)} 
        ACCESS read-only 
        STATUS mandatory 
        DESCRIPTION 
            "If set(1) the 'service / blocked' display 
             on bus unit 5  is steady on." 
        ::= { objectEntry 24624067 }
        
    rsBU05FailureDisplayBlinking            OBJECT-TYPE 
        SYNTAX INTEGER  { off(0),blinking(1) } 
        ACCESS read-only 
        STATUS mandatory 
        DESCRIPTION 
            "If set(1) the 'failure' display 
             on bus unit 5 is blinking." 
        ::= { objectEntry 24624068 }
        
    rsBU05FailureDisplayOn                  OBJECT-TYPE 
        SYNTAX INTEGER  { off(0),on(1)} 
        ACCESS read-only 
        STATUS mandatory 
        DESCRIPTION 
            "If set(1) the 'failure' display 
             on bus unit 5  is steady on." 
        ::= { objectEntry 24624069 }
        
    rsBU05OperatingDisplayBlinking          OBJECT-TYPE 
        SYNTAX INTEGER  { off(0),blinking(1) } 
        ACCESS read-only 
        STATUS mandatory 
        DESCRIPTION 
            "If set(1) the 'operating' display 
             on bus unit 5 is blinking." 
        ::= { objectEntry 24624070 }
        
    rsBU05OperatingDisplayOn                OBJECT-TYPE 
        SYNTAX INTEGER  { off(0),on(1)} 
        ACCESS read-only 
        STATUS mandatory 
        DESCRIPTION 
            "If set(1) the 'operating' display 
             on bus unit 5  is steady on." 
        ::= { objectEntry 24624071 }
        
    rsBU05ManualActivationDisplayBlinking   OBJECT-TYPE 
        SYNTAX INTEGER  { off(0),blinking(1) } 
        ACCESS read-only 
        STATUS mandatory 
        DESCRIPTION 
            "If set(1) the 'manual activation' display 
             on bus unit 5 is blinking." 
        ::= { objectEntry 24624072 }
        
    rsBU05ManualActivationDisplayOn         OBJECT-TYPE 
        SYNTAX INTEGER  { off(0),on(1)} 
        ACCESS read-only 
        STATUS mandatory 
        DESCRIPTION 
            "If set(1) the 'manual activation' display 
             on bus unit 5  is steady on." 
        ::= { objectEntry 24624073 }
        
    rsBU05OnlineDisplayDisplayOn            OBJECT-TYPE 
        SYNTAX INTEGER  { off(0),on(1)} 
        ACCESS read-only 
        STATUS mandatory 
        DESCRIPTION 
            "If set(1) the 'online' display 
             on bus unit 5  is steady on." 
        ::= { objectEntry 24624074 }
        
    rsBU05IgnitionLineActivatedDisplayOn    OBJECT-TYPE 
        SYNTAX INTEGER  { off(0),on(1)} 
        ACCESS read-only 
        STATUS mandatory 
        DESCRIPTION 
            "If set(1) the 'ignition line activated' display 
             on bus unit 5  is steady on." 
        ::= { objectEntry 24624075 }
        
    rsBU05CutOffLineActivatedDisplayOn      OBJECT-TYPE 
        SYNTAX INTEGER  { off(0),on(1)} 
        ACCESS read-only 
        STATUS mandatory 
        DESCRIPTION 
            "If set(1) the 'cut-off line activated' display 
             on bus unit 5  is steady on." 
        ::= { objectEntry 24624076 }
        
    rsBU05DoorSwitchDisplayOn               OBJECT-TYPE 
        SYNTAX INTEGER  { off(0),on(1)} 
        ACCESS read-only 
        STATUS mandatory 
        DESCRIPTION 
            "If set(1) the 'door switch' display 
             on bus unit 5  is steady on." 
        ::= { objectEntry 24624077 }
        
    rsBU05Bit14                             OBJECT-TYPE 
        SYNTAX INTEGER  { off(0),on(1)} 
        ACCESS read-only 
        STATUS mandatory 
        DESCRIPTION 
            "Unused bit." 
        ::= { objectEntry 24624078 }
        
    rsBU05Bit15                             OBJECT-TYPE 
        SYNTAX INTEGER  { off(0),on(1)} 
        ACCESS read-only 
        STATUS mandatory 
        DESCRIPTION 
            "Unused bit." 
        ::= { objectEntry 24624079 }
        
    rsBU06ActivatedDisplayBlinking          OBJECT-TYPE 
        SYNTAX INTEGER  { off(0),blinking(1) } 
        ACCESS read-only 
        STATUS mandatory 
        DESCRIPTION 
            "If set(1) the 'activated' display 
             on bus unit 6 is blinking." 
        ::= { objectEntry 24624080 }
        
    rsBU06ActivatedDisplayOn                OBJECT-TYPE 
        SYNTAX INTEGER  { off(0),on(1)} 
        ACCESS read-only 
        STATUS mandatory 
        DESCRIPTION 
            "If set(1) the 'activated' display
             on bus unit 6  is steady on." 
        ::= { objectEntry 24624081 }
        
    rsBU06ServiceDisplayBlinking            OBJECT-TYPE 
        SYNTAX INTEGER  { off(0),blinking(1) } 
        ACCESS read-only 
        STATUS mandatory 
        DESCRIPTION 
            "If set(1) the 'service / blocked' display 
             on bus unit 6 is blinking." 
        ::= { objectEntry 24624082 }
        
    rsBU06ServiceDisplayOn                  OBJECT-TYPE 
        SYNTAX INTEGER  { off(0),on(1)} 
        ACCESS read-only 
        STATUS mandatory 
        DESCRIPTION 
            "If set(1) the 'service / blocked' display 
             on bus unit 6  is steady on." 
        ::= { objectEntry 24624083 }
        
    rsBU06FailureDisplayBlinking            OBJECT-TYPE 
        SYNTAX INTEGER  { off(0),blinking(1) } 
        ACCESS read-only 
        STATUS mandatory 
        DESCRIPTION 
            "If set(1) the 'failure' display 
             on bus unit 6 is blinking." 
        ::= { objectEntry 24624084 }
        
    rsBU06FailureDisplayOn                  OBJECT-TYPE 
        SYNTAX INTEGER  { off(0),on(1)} 
        ACCESS read-only 
        STATUS mandatory 
        DESCRIPTION 
            "If set(1) the 'failure' display 
             on bus unit 6  is steady on." 
        ::= { objectEntry 24624085 }
        
    rsBU06OperatingDisplayBlinking          OBJECT-TYPE 
        SYNTAX INTEGER  { off(0),blinking(1) } 
        ACCESS read-only 
        STATUS mandatory 
        DESCRIPTION 
            "If set(1) the 'operating' display 
             on bus unit 6 is blinking." 
        ::= { objectEntry 24624086 }
        
    rsBU06OperatingDisplayOn                OBJECT-TYPE 
        SYNTAX INTEGER  { off(0),on(1)} 
        ACCESS read-only 
        STATUS mandatory 
        DESCRIPTION 
            "If set(1) the 'operating' display 
             on bus unit 6  is steady on." 
        ::= { objectEntry 24624087 }
        
    rsBU06ManualActivationDisplayBlinking   OBJECT-TYPE 
        SYNTAX INTEGER  { off(0),blinking(1) } 
        ACCESS read-only 
        STATUS mandatory 
        DESCRIPTION 
            "If set(1) the 'manual activation' display 
             on bus unit 6 is blinking." 
        ::= { objectEntry 24624088 }
        
    rsBU06ManualActivationDisplayOn         OBJECT-TYPE 
        SYNTAX INTEGER  { off(0),on(1)} 
        ACCESS read-only 
        STATUS mandatory 
        DESCRIPTION 
            "If set(1) the 'manual activation' display 
             on bus unit 6  is steady on." 
        ::= { objectEntry 24624089 }
        
    rsBU06OnlineDisplayDisplayOn            OBJECT-TYPE 
        SYNTAX INTEGER  { off(0),on(1)} 
        ACCESS read-only 
        STATUS mandatory 
        DESCRIPTION 
            "If set(1) the 'online' display 
             on bus unit 6  is steady on." 
        ::= { objectEntry 24624090 }
        
    rsBU06IgnitionLineActivatedDisplayOn    OBJECT-TYPE 
        SYNTAX INTEGER  { off(0),on(1)} 
        ACCESS read-only 
        STATUS mandatory 
        DESCRIPTION 
            "If set(1) the 'ignition line activated' display 
             on bus unit 6  is steady on." 
        ::= { objectEntry 24624091 }
        
    rsBU06CutOffLineActivatedDisplayOn      OBJECT-TYPE 
        SYNTAX INTEGER  { off(0),on(1)} 
        ACCESS read-only 
        STATUS mandatory 
        DESCRIPTION 
            "If set(1) the 'cut-off line activated' display 
             on bus unit 6  is steady on." 
        ::= { objectEntry 24624092 }
        
    rsBU06DoorSwitchDisplayOn               OBJECT-TYPE 
        SYNTAX INTEGER  { off(0),on(1)} 
        ACCESS read-only 
        STATUS mandatory 
        DESCRIPTION 
            "If set(1) the 'door switch' display 
             on bus unit 6  is steady on." 
        ::= { objectEntry 24624093 }
        
    rsBU06Bit14                             OBJECT-TYPE 
        SYNTAX INTEGER  { off(0),on(1)} 
        ACCESS read-only 
        STATUS mandatory 
        DESCRIPTION 
            "Unused bit." 
        ::= { objectEntry 24624094 }
        
    rsBU06Bit15                             OBJECT-TYPE 
        SYNTAX INTEGER  { off(0),on(1)} 
        ACCESS read-only 
        STATUS mandatory 
        DESCRIPTION 
            "Unused bit." 
        ::= { objectEntry 24624095 }
        
    rsBU07ActivatedDisplayBlinking          OBJECT-TYPE 
        SYNTAX INTEGER  { off(0),blinking(1) } 
        ACCESS read-only 
        STATUS mandatory 
        DESCRIPTION 
            "If set(1) the 'activated' display 
             on bus unit 7 is blinking." 
        ::= { objectEntry 24624096 }
        
    rsBU07ActivatedDisplayOn                OBJECT-TYPE 
        SYNTAX INTEGER  { off(0),on(1)} 
        ACCESS read-only 
        STATUS mandatory 
        DESCRIPTION 
            "If set(1) the 'activated' display
             on bus unit 7  is steady on." 
        ::= { objectEntry 24624097 }
        
    rsBU07ServiceDisplayBlinking            OBJECT-TYPE 
        SYNTAX INTEGER  { off(0),blinking(1) } 
        ACCESS read-only 
        STATUS mandatory 
        DESCRIPTION 
            "If set(1) the 'service / blocked' display 
             on bus unit 7 is blinking." 
        ::= { objectEntry 24624098 }
        
    rsBU07ServiceDisplayOn                  OBJECT-TYPE 
        SYNTAX INTEGER  { off(0),on(1)} 
        ACCESS read-only 
        STATUS mandatory 
        DESCRIPTION 
            "If set(1) the 'service / blocked' display 
             on bus unit 7  is steady on." 
        ::= { objectEntry 24624099 }
        
    rsBU07FailureDisplayBlinking            OBJECT-TYPE 
        SYNTAX INTEGER  { off(0),blinking(1) } 
        ACCESS read-only 
        STATUS mandatory 
        DESCRIPTION 
            "If set(1) the 'failure' display 
             on bus unit 7 is blinking." 
        ::= { objectEntry 24624100 }
        
    rsBU07FailureDisplayOn                  OBJECT-TYPE 
        SYNTAX INTEGER  { off(0),on(1)} 
        ACCESS read-only 
        STATUS mandatory 
        DESCRIPTION 
            "If set(1) the 'failure' display 
             on bus unit 7  is steady on." 
        ::= { objectEntry 24624101 }
        
    rsBU07OperatingDisplayBlinking          OBJECT-TYPE 
        SYNTAX INTEGER  { off(0),blinking(1) } 
        ACCESS read-only 
        STATUS mandatory 
        DESCRIPTION 
            "If set(1) the 'operating' display 
             on bus unit 7 is blinking." 
        ::= { objectEntry 24624102 }
        
    rsBU07OperatingDisplayOn                OBJECT-TYPE 
        SYNTAX INTEGER  { off(0),on(1)} 
        ACCESS read-only 
        STATUS mandatory 
        DESCRIPTION 
            "If set(1) the 'operating' display 
             on bus unit 7  is steady on." 
        ::= { objectEntry 24624103 }
        
    rsBU07ManualActivationDisplayBlinking   OBJECT-TYPE 
        SYNTAX INTEGER  { off(0),blinking(1) } 
        ACCESS read-only 
        STATUS mandatory 
        DESCRIPTION 
            "If set(1) the 'manual activation' display 
             on bus unit 7 is blinking." 
        ::= { objectEntry 24624104 }
        
    rsBU07ManualActivationDisplayOn         OBJECT-TYPE 
        SYNTAX INTEGER  { off(0),on(1)} 
        ACCESS read-only 
        STATUS mandatory 
        DESCRIPTION 
            "If set(1) the 'manual activation' display 
             on bus unit 7  is steady on." 
        ::= { objectEntry 24624105 }
        
    rsBU07OnlineDisplayDisplayOn            OBJECT-TYPE 
        SYNTAX INTEGER  { off(0),on(1)} 
        ACCESS read-only 
        STATUS mandatory 
        DESCRIPTION 
            "If set(1) the 'online' display 
             on bus unit 7  is steady on." 
        ::= { objectEntry 24624106 }
        
    rsBU07IgnitionLineActivatedDisplayOn    OBJECT-TYPE 
        SYNTAX INTEGER  { off(0),on(1)} 
        ACCESS read-only 
        STATUS mandatory 
        DESCRIPTION 
            "If set(1) the 'ignition line activated' display 
             on bus unit 7  is steady on." 
        ::= { objectEntry 24624107 }
        
    rsBU07CutOffLineActivatedDisplayOn      OBJECT-TYPE 
        SYNTAX INTEGER  { off(0),on(1)} 
        ACCESS read-only 
        STATUS mandatory 
        DESCRIPTION 
            "If set(1) the 'cut-off line activated' display 
             on bus unit 7  is steady on." 
        ::= { objectEntry 24624108 }
        
    rsBU07DoorSwitchDisplayOn               OBJECT-TYPE 
        SYNTAX INTEGER  { off(0),on(1)} 
        ACCESS read-only 
        STATUS mandatory 
        DESCRIPTION 
            "If set(1) the 'door switch' display 
             on bus unit 7  is steady on." 
        ::= { objectEntry 24624109 }
        
    rsBU07Bit14                             OBJECT-TYPE 
        SYNTAX INTEGER  { off(0),on(1)} 
        ACCESS read-only 
        STATUS mandatory 
        DESCRIPTION 
            "Unused bit." 
        ::= { objectEntry 24624110 }
        
    rsBU07Bit15                             OBJECT-TYPE 
        SYNTAX INTEGER  { off(0),on(1)} 
        ACCESS read-only 
        STATUS mandatory 
        DESCRIPTION 
            "Unused bit." 
        ::= { objectEntry 24624111 }
        
    rsBU08ActivatedDisplayBlinking          OBJECT-TYPE 
        SYNTAX INTEGER  { off(0),blinking(1) } 
        ACCESS read-only 
        STATUS mandatory 
        DESCRIPTION 
            "If set(1) the 'activated' display 
             on bus unit 8 is blinking." 
        ::= { objectEntry 24624112 }
        
    rsBU08ActivatedDisplayOn                OBJECT-TYPE 
        SYNTAX INTEGER  { off(0),on(1)} 
        ACCESS read-only 
        STATUS mandatory 
        DESCRIPTION 
            "If set(1) the 'activated' display
             on bus unit 8  is steady on." 
        ::= { objectEntry 24624113 }
        
    rsBU08ServiceDisplayBlinking            OBJECT-TYPE 
        SYNTAX INTEGER  { off(0),blinking(1) } 
        ACCESS read-only 
        STATUS mandatory 
        DESCRIPTION 
            "If set(1) the 'service / blocked' display 
             on bus unit 8 is blinking." 
        ::= { objectEntry 24624114 }
        
    rsBU08ServiceDisplayOn                  OBJECT-TYPE 
        SYNTAX INTEGER  { off(0),on(1)} 
        ACCESS read-only 
        STATUS mandatory 
        DESCRIPTION 
            "If set(1) the 'service / blocked' display 
             on bus unit 8  is steady on." 
        ::= { objectEntry 24624115 }
        
    rsBU08FailureDisplayBlinking            OBJECT-TYPE 
        SYNTAX INTEGER  { off(0),blinking(1) } 
        ACCESS read-only 
        STATUS mandatory 
        DESCRIPTION 
            "If set(1) the 'failure' display 
             on bus unit 8 is blinking." 
        ::= { objectEntry 24624116 }
        
    rsBU08FailureDisplayOn                  OBJECT-TYPE 
        SYNTAX INTEGER  { off(0),on(1)} 
        ACCESS read-only 
        STATUS mandatory 
        DESCRIPTION 
            "If set(1) the 'failure' display 
             on bus unit 8  is steady on." 
        ::= { objectEntry 24624117 }
        
    rsBU08OperatingDisplayBlinking          OBJECT-TYPE 
        SYNTAX INTEGER  { off(0),blinking(1) } 
        ACCESS read-only 
        STATUS mandatory 
        DESCRIPTION 
            "If set(1) the 'operating' display 
             on bus unit 8 is blinking." 
        ::= { objectEntry 24624118 }
        
    rsBU08OperatingDisplayOn                OBJECT-TYPE 
        SYNTAX INTEGER  { off(0),on(1)} 
        ACCESS read-only 
        STATUS mandatory 
        DESCRIPTION 
            "If set(1) the 'operating' display 
             on bus unit 8  is steady on." 
        ::= { objectEntry 24624119 }
        
    rsBU08ManualActivationDisplayBlinking   OBJECT-TYPE 
        SYNTAX INTEGER  { off(0),blinking(1) } 
        ACCESS read-only 
        STATUS mandatory 
        DESCRIPTION 
            "If set(1) the 'manual activation' display 
             on bus unit 8 is blinking." 
        ::= { objectEntry 24624120 }
        
    rsBU08ManualActivationDisplayOn         OBJECT-TYPE 
        SYNTAX INTEGER  { off(0),on(1)} 
        ACCESS read-only 
        STATUS mandatory 
        DESCRIPTION 
            "If set(1) the 'manual activation' display 
             on bus unit 8  is steady on." 
        ::= { objectEntry 24624121 }
        
    rsBU08OnlineDisplayDisplayOn            OBJECT-TYPE 
        SYNTAX INTEGER  { off(0),on(1)} 
        ACCESS read-only 
        STATUS mandatory 
        DESCRIPTION 
            "If set(1) the 'online' display 
             on bus unit 8  is steady on." 
        ::= { objectEntry 24624122 }
        
    rsBU08IgnitionLineActivatedDisplayOn    OBJECT-TYPE 
        SYNTAX INTEGER  { off(0),on(1)} 
        ACCESS read-only 
        STATUS mandatory 
        DESCRIPTION 
            "If set(1) the 'ignition line activated' display 
             on bus unit 8  is steady on." 
        ::= { objectEntry 24624123 }
        
    rsBU08CutOffLineActivatedDisplayOn      OBJECT-TYPE 
        SYNTAX INTEGER  { off(0),on(1)} 
        ACCESS read-only 
        STATUS mandatory 
        DESCRIPTION 
            "If set(1) the 'cut-off line activated' display 
             on bus unit 8  is steady on." 
        ::= { objectEntry 24624124 }
        
    rsBU08DoorSwitchDisplayOn               OBJECT-TYPE 
        SYNTAX INTEGER  { off(0),on(1)} 
        ACCESS read-only 
        STATUS mandatory 
        DESCRIPTION 
            "If set(1) the 'door switch' display 
             on bus unit 8  is steady on." 
        ::= { objectEntry 24624125 }
        
    rsBU08Bit14                             OBJECT-TYPE 
        SYNTAX INTEGER  { off(0),on(1)} 
        ACCESS read-only 
        STATUS mandatory 
        DESCRIPTION 
            "Unused bit." 
        ::= { objectEntry 24624126 }
        
    rsBU08Bit15                             OBJECT-TYPE 
        SYNTAX INTEGER  { off(0),on(1)} 
        ACCESS read-only 
        STATUS mandatory 
        DESCRIPTION 
            "Unused bit." 
        ::= { objectEntry 24624127 }
        
    rsBU09ActivatedDisplayBlinking          OBJECT-TYPE 
        SYNTAX INTEGER  { off(0),blinking(1) } 
        ACCESS read-only 
        STATUS mandatory 
        DESCRIPTION 
            "If set(1) the 'activated' display 
             on bus unit 9 is blinking." 
        ::= { objectEntry 24624128 }
        
    rsBU09ActivatedDisplayOn                OBJECT-TYPE 
        SYNTAX INTEGER  { off(0),on(1)} 
        ACCESS read-only 
        STATUS mandatory 
        DESCRIPTION 
            "If set(1) the 'activated' display
             on bus unit 9  is steady on." 
        ::= { objectEntry 24624129 }
        
    rsBU09ServiceDisplayBlinking            OBJECT-TYPE 
        SYNTAX INTEGER  { off(0),blinking(1) } 
        ACCESS read-only 
        STATUS mandatory 
        DESCRIPTION 
            "If set(1) the 'service / blocked' display 
             on bus unit 9 is blinking." 
        ::= { objectEntry 24624130 }
        
    rsBU09ServiceDisplayOn                  OBJECT-TYPE 
        SYNTAX INTEGER  { off(0),on(1)} 
        ACCESS read-only 
        STATUS mandatory 
        DESCRIPTION 
            "If set(1) the 'service / blocked' display 
             on bus unit 9  is steady on." 
        ::= { objectEntry 24624131 }
        
    rsBU09FailureDisplayBlinking            OBJECT-TYPE 
        SYNTAX INTEGER  { off(0),blinking(1) } 
        ACCESS read-only 
        STATUS mandatory 
        DESCRIPTION 
            "If set(1) the 'failure' display 
             on bus unit 9 is blinking." 
        ::= { objectEntry 24624132 }
        
    rsBU09FailureDisplayOn                  OBJECT-TYPE 
        SYNTAX INTEGER  { off(0),on(1)} 
        ACCESS read-only 
        STATUS mandatory 
        DESCRIPTION 
            "If set(1) the 'failure' display 
             on bus unit 9  is steady on." 
        ::= { objectEntry 24624133 }
        
    rsBU09OperatingDisplayBlinking          OBJECT-TYPE 
        SYNTAX INTEGER  { off(0),blinking(1) } 
        ACCESS read-only 
        STATUS mandatory 
        DESCRIPTION 
            "If set(1) the 'operating' display 
             on bus unit 9 is blinking." 
        ::= { objectEntry 24624134 }
        
    rsBU09OperatingDisplayOn                OBJECT-TYPE 
        SYNTAX INTEGER  { off(0),on(1)} 
        ACCESS read-only 
        STATUS mandatory 
        DESCRIPTION 
            "If set(1) the 'operating' display 
             on bus unit 9  is steady on." 
        ::= { objectEntry 24624135 }
        
    rsBU09ManualActivationDisplayBlinking   OBJECT-TYPE 
        SYNTAX INTEGER  { off(0),blinking(1) } 
        ACCESS read-only 
        STATUS mandatory 
        DESCRIPTION 
            "If set(1) the 'manual activation' display 
             on bus unit 9 is blinking." 
        ::= { objectEntry 24624136 }
        
    rsBU09ManualActivationDisplayOn         OBJECT-TYPE 
        SYNTAX INTEGER  { off(0),on(1)} 
        ACCESS read-only 
        STATUS mandatory 
        DESCRIPTION 
            "If set(1) the 'manual activation' display 
             on bus unit 9  is steady on." 
        ::= { objectEntry 24624137 }
        
    rsBU09OnlineDisplayDisplayOn            OBJECT-TYPE 
        SYNTAX INTEGER  { off(0),on(1)} 
        ACCESS read-only 
        STATUS mandatory 
        DESCRIPTION 
            "If set(1) the 'online' display 
             on bus unit 9  is steady on." 
        ::= { objectEntry 24624138 }
        
    rsBU09IgnitionLineActivatedDisplayOn    OBJECT-TYPE 
        SYNTAX INTEGER  { off(0),on(1)} 
        ACCESS read-only 
        STATUS mandatory 
        DESCRIPTION 
            "If set(1) the 'ignition line activated' display 
             on bus unit 9  is steady on." 
        ::= { objectEntry 24624139 }
        
    rsBU09CutOffLineActivatedDisplayOn      OBJECT-TYPE 
        SYNTAX INTEGER  { off(0),on(1)} 
        ACCESS read-only 
        STATUS mandatory 
        DESCRIPTION 
            "If set(1) the 'cut-off line activated' display 
             on bus unit 9  is steady on." 
        ::= { objectEntry 24624140 }
        
    rsBU09DoorSwitchDisplayOn               OBJECT-TYPE 
        SYNTAX INTEGER  { off(0),on(1)} 
        ACCESS read-only 
        STATUS mandatory 
        DESCRIPTION 
            "If set(1) the 'door switch' display 
             on bus unit 9  is steady on." 
        ::= { objectEntry 24624141 }
        
    rsBU09Bit14                             OBJECT-TYPE 
        SYNTAX INTEGER  { off(0),on(1)} 
        ACCESS read-only 
        STATUS mandatory 
        DESCRIPTION 
            "Unused bit." 
        ::= { objectEntry 24624142 }
        
    rsBU09Bit15                             OBJECT-TYPE 
        SYNTAX INTEGER  { off(0),on(1)} 
        ACCESS read-only 
        STATUS mandatory 
        DESCRIPTION 
            "Unused bit." 
        ::= { objectEntry 24624143 }
        
    rsBU10ActivatedDisplayBlinking          OBJECT-TYPE 
        SYNTAX INTEGER  { off(0),blinking(1) } 
        ACCESS read-only 
        STATUS mandatory 
        DESCRIPTION 
            "If set(1) the 'activated' display 
             on bus unit 10 is blinking." 
        ::= { objectEntry 24624144 }
        
    rsBU10ActivatedDisplayOn                OBJECT-TYPE 
        SYNTAX INTEGER  { off(0),on(1)} 
        ACCESS read-only 
        STATUS mandatory 
        DESCRIPTION 
            "If set(1) the 'activated' display
             on bus unit 10  is steady on." 
        ::= { objectEntry 24624145 }
        
    rsBU10ServiceDisplayBlinking            OBJECT-TYPE 
        SYNTAX INTEGER  { off(0),blinking(1) } 
        ACCESS read-only 
        STATUS mandatory 
        DESCRIPTION 
            "If set(1) the 'service / blocked' display 
             on bus unit 10 is blinking." 
        ::= { objectEntry 24624146 }
        
    rsBU10ServiceDisplayOn                  OBJECT-TYPE 
        SYNTAX INTEGER  { off(0),on(1)} 
        ACCESS read-only 
        STATUS mandatory 
        DESCRIPTION 
            "If set(1) the 'service / blocked' display 
             on bus unit 10  is steady on." 
        ::= { objectEntry 24624147 }
        
    rsBU10FailureDisplayBlinking            OBJECT-TYPE 
        SYNTAX INTEGER  { off(0),blinking(1) } 
        ACCESS read-only 
        STATUS mandatory 
        DESCRIPTION 
            "If set(1) the 'failure' display 
             on bus unit 10 is blinking." 
        ::= { objectEntry 24624148 }
        
    rsBU10FailureDisplayOn                  OBJECT-TYPE 
        SYNTAX INTEGER  { off(0),on(1)} 
        ACCESS read-only 
        STATUS mandatory 
        DESCRIPTION 
            "If set(1) the 'failure' display 
             on bus unit 10  is steady on." 
        ::= { objectEntry 24624149 }
        
    rsBU10OperatingDisplayBlinking          OBJECT-TYPE 
        SYNTAX INTEGER  { off(0),blinking(1) } 
        ACCESS read-only 
        STATUS mandatory 
        DESCRIPTION 
            "If set(1) the 'operating' display 
             on bus unit 10 is blinking." 
        ::= { objectEntry 24624150 }
        
    rsBU10OperatingDisplayOn                OBJECT-TYPE 
        SYNTAX INTEGER  { off(0),on(1)} 
        ACCESS read-only 
        STATUS mandatory 
        DESCRIPTION 
            "If set(1) the 'operating' display 
             on bus unit 10  is steady on." 
        ::= { objectEntry 24624151 }
        
    rsBU10ManualActivationDisplayBlinking   OBJECT-TYPE 
        SYNTAX INTEGER  { off(0),blinking(1) } 
        ACCESS read-only 
        STATUS mandatory 
        DESCRIPTION 
            "If set(1) the 'manual activation' display 
             on bus unit 10 is blinking." 
        ::= { objectEntry 24624152 }
        
    rsBU10ManualActivationDisplayOn         OBJECT-TYPE 
        SYNTAX INTEGER  { off(0),on(1)} 
        ACCESS read-only 
        STATUS mandatory 
        DESCRIPTION 
            "If set(1) the 'manual activation' display 
             on bus unit 10  is steady on." 
        ::= { objectEntry 24624153 }
        
    rsBU10OnlineDisplayDisplayOn            OBJECT-TYPE 
        SYNTAX INTEGER  { off(0),on(1)} 
        ACCESS read-only 
        STATUS mandatory 
        DESCRIPTION 
            "If set(1) the 'online' display 
             on bus unit 10  is steady on." 
        ::= { objectEntry 24624154 }
        
    rsBU10IgnitionLineActivatedDisplayOn    OBJECT-TYPE 
        SYNTAX INTEGER  { off(0),on(1)} 
        ACCESS read-only 
        STATUS mandatory 
        DESCRIPTION 
            "If set(1) the 'ignition line activated' display 
             on bus unit 10  is steady on." 
        ::= { objectEntry 24624155 }
        
    rsBU10CutOffLineActivatedDisplayOn      OBJECT-TYPE 
        SYNTAX INTEGER  { off(0),on(1)} 
        ACCESS read-only 
        STATUS mandatory 
        DESCRIPTION 
            "If set(1) the 'cut-off line activated' display 
             on bus unit 10  is steady on." 
        ::= { objectEntry 24624156 }
        
    rsBU10DoorSwitchDisplayOn               OBJECT-TYPE 
        SYNTAX INTEGER  { off(0),on(1)} 
        ACCESS read-only 
        STATUS mandatory 
        DESCRIPTION 
            "If set(1) the 'door switch' display 
             on bus unit 10  is steady on." 
        ::= { objectEntry 24624157 }
        
    rsBU10Bit14                             OBJECT-TYPE 
        SYNTAX INTEGER  { off(0),on(1)} 
        ACCESS read-only 
        STATUS mandatory 
        DESCRIPTION 
            "Unused bit." 
        ::= { objectEntry 24624158 }
        
    rsBU10Bit15                             OBJECT-TYPE 
        SYNTAX INTEGER  { off(0),on(1)} 
        ACCESS read-only 
        STATUS mandatory 
        DESCRIPTION 
            "Unused bit." 
        ::= { objectEntry 24624159 }
        
        
    ----------------------------------------------------
    -- Bits from RackSens data object 24625 (6031 hex)
    ----------------------------------------------------

    rsCtrlBit00                             OBJECT-TYPE 
        SYNTAX INTEGER  { off(0),on(1)} 
        ACCESS read-only
        STATUS mandatory 
        DESCRIPTION 
            "Unused bit." 
        ::= { objectEntry 24625000 }
        
    rsCtrlBit01                             OBJECT-TYPE 
        SYNTAX INTEGER  { off(0),on(1)} 
        ACCESS read-only
        STATUS mandatory 
        DESCRIPTION 
            "Unused bit." 
        ::= { objectEntry 24625001 }
        
    rsCtrlBit02                             OBJECT-TYPE 
        SYNTAX INTEGER  { off(0),on(1)} 
        ACCESS read-only
        STATUS mandatory 
        DESCRIPTION 
            "Unused bit." 
        ::= { objectEntry 24625002 }
        
    rsCtrlBit03                             OBJECT-TYPE 
        SYNTAX INTEGER  { off(0),on(1)} 
        ACCESS read-only
        STATUS mandatory 
        DESCRIPTION 
            "Unused bit." 
        ::= { objectEntry 24625003 }
        
    rsCtrlBit04                             OBJECT-TYPE 
        SYNTAX INTEGER  { off(0),on(1)} 
        ACCESS read-only
        STATUS mandatory 
        DESCRIPTION 
            "Unused bit." 
        ::= { objectEntry 24625004 }
        
    rsBuzzerReset                           OBJECT-TYPE 
        SYNTAX INTEGER  { off(0),on(1)} 
        ACCESS read-only
        STATUS mandatory 
        DESCRIPTION 
            "Unused bit." 
        ::= { objectEntry 24625005 }
        
    rsMessageStorageReset                   OBJECT-TYPE 
        SYNTAX INTEGER  { off(0),on(1)} 
        ACCESS read-only
        STATUS mandatory 
        DESCRIPTION 
            "Unused bit." 
        ::= { objectEntry 24625006 }
        
    rsAlarmAndFailureReset                  OBJECT-TYPE 
        SYNTAX INTEGER  { off(0),on(1)} 
        ACCESS read-only
        STATUS mandatory 
        DESCRIPTION 
            "Unused bit." 
        ::= { objectEntry 24625007 }
        
                                                                                                                                                                         
    --------------------------------------------------------------------------------------------
    -- Float value from data object 24580 (6004 hex) as string, integer and multiplied by 100 --
    --------------------------------------------------------------------------------------------

    rsTemperature1String        OBJECT-TYPE 
        SYNTAX OCTET STRING    
        ACCESS read-only 
        STATUS mandatory 
        DESCRIPTION 
            "The temperature on sensor 1 in Celsius, as string."
        ::= { objectEntry 245800000 }
        
    rsTemperature1Integer       OBJECT-TYPE 
        SYNTAX INTEGER         
        ACCESS read-only 
        STATUS mandatory 
        DESCRIPTION 
            "The temperature on sensor 1 in Celsius, as integer."
        ::= { objectEntry 245800001 }
        
    rsTemperature1IntMul100     OBJECT-TYPE 
        SYNTAX INTEGER         
        ACCESS read-only 
        STATUS mandatory 
        DESCRIPTION 
            "The temperature on sensor 1 in Celsius multiplied by 100, as integer."
        ::= { objectEntry 245800002 }

    --------------------------------------------------------------------------------------------
    -- Float value from data object 24581 (6005 hex) as string, integer and multiplied by 100 --
    --------------------------------------------------------------------------------------------

    rsTemperature2String        OBJECT-TYPE 
        SYNTAX OCTET STRING    
        ACCESS read-only 
        STATUS mandatory 
        DESCRIPTION 
            "The temperature on sensor 2 in Celsius, as string."
        ::= { objectEntry 245810000 }
                
    rsTemperature2Integer       OBJECT-TYPE 
        SYNTAX INTEGER         
        ACCESS read-only 
        STATUS mandatory 
        DESCRIPTION 
            "The temperature on sensor 2 in Celsius, as integer."
        ::= { objectEntry 245810001 }
                
    rsTemperature2IntMul100     OBJECT-TYPE 
        SYNTAX INTEGER         
        ACCESS read-only 
        STATUS mandatory 
        DESCRIPTION 
            "The temperature on sensor 2 in Celsius multiplied by 100, as integer."
        ::= { objectEntry 245810002 }

    --------------------------------------------------------------------------------------------
    -- Float value from data object 24582 (6006 hex) as string, integer and multiplied by 100 --
    --------------------------------------------------------------------------------------------

    rsTemperature3String        OBJECT-TYPE 
        SYNTAX OCTET 
        STRING    ACCESS read-only 
        STATUS mandatory 
        DESCRIPTION 
            "The temperature on sensor 3 in Celsius, as string."
        ::= { objectEntry 245820000 }
                
    rsTemperature3Integer       OBJECT-TYPE 
        SYNTAX INTEGER         
        ACCESS read-only 
        STATUS mandatory 
        DESCRIPTION 
            "The temperature on sensor 3 in Celsius, as integer."
        ::= { objectEntry 245820001 }
                
    rsTemperature3IntMul100     OBJECT-TYPE 
        SYNTAX INTEGER         
        ACCESS read-only 
        STATUS mandatory 
        DESCRIPTION 
            "The temperature on sensor 3 in Celsius multiplied by 100, as integer."
        ::= { objectEntry 245820002 }
                
    --------------------------------------------------------------------------------------------
    -- Float value from data object 24583 (6007 hex) as string, integer and multiplied by 100 --
    --------------------------------------------------------------------------------------------

    rsTemperature4String        OBJECT-TYPE 
        SYNTAX OCTET STRING    
        ACCESS read-only 
        STATUS mandatory 
        DESCRIPTION 
            "The temperature on sensor 4 in Celsius, as string."
        ::= { objectEntry 245830000 }
    
    rsTemperature4Integer       OBJECT-TYPE 
        SYNTAX INTEGER         
        ACCESS read-only 
        STATUS mandatory 
        DESCRIPTION 
            "The temperature on sensor 4 in Celsius, as integer."
        ::= { objectEntry 245830001 }
        
    rsTemperature4IntMul100     OBJECT-TYPE 
        SYNTAX INTEGER         
        ACCESS read-only 
        STATUS mandatory 
        DESCRIPTION 
            "The temperature on sensor 4 in Celsius multiplied by 100, as integer."
        ::= { objectEntry 245830002 }

    --------------------------------------------------------------------------------------------
    -- Float value from data object 24584 (6008 hex) as string, integer and multiplied by 100 --
    --------------------------------------------------------------------------------------------

    rsTemperature5String        OBJECT-TYPE 
        SYNTAX OCTET STRING    
        ACCESS read-only 
        STATUS mandatory 
        DESCRIPTION 
            "The temperature on sensor 5 in Celsius, as string."
        ::= { objectEntry 245840000 }
    
    rsTemperature5Integer       OBJECT-TYPE 
        SYNTAX INTEGER         
        ACCESS read-only 
        STATUS mandatory 
        DESCRIPTION 
            "The temperature on sensor 5 in Celsius, as integer."
        ::= { objectEntry 245840001 }
        
    rsTemperature5IntMul100     OBJECT-TYPE 
        SYNTAX INTEGER         
        ACCESS read-only 
        STATUS mandatory 
        DESCRIPTION 
            "The temperature on sensor 5 in Celsius multiplied by 100, as integer."
        ::= { objectEntry 245840002 }

    --------------------------------------------------------------------------------------------
    -- Float value from data object 24585 (6009 hex) as string, integer and multiplied by 100 --
    --------------------------------------------------------------------------------------------

    rsAirTemperatureString      OBJECT-TYPE 
        SYNTAX OCTET STRING    
        ACCESS read-only 
        STATUS mandatory 
        DESCRIPTION 
            "The air temperature in Celsius, as string."
        ::= { objectEntry 245850000 }
    
    rsAirTemperatureInteger     OBJECT-TYPE 
        SYNTAX INTEGER         
        ACCESS read-only 
        STATUS mandatory 
        DESCRIPTION 
            "The air temperature in Celsius, as integer."
        ::= { objectEntry 245850001 }
        
    rsAirTemperatureIntMul100   OBJECT-TYPE 
        SYNTAX INTEGER         
        ACCESS read-only 
        STATUS mandatory 
        DESCRIPTION 
            "The air temperature in Celsius multiplied by 100, as integer."
        ::= { objectEntry 245850002 }

    --------------------------------------------------------------------------------------------
    -- Float value from data object 24586 (600A hex) as string, integer and multiplied by 100 --
    --------------------------------------------------------------------------------------------

    rsAirFlowSpeedString        OBJECT-TYPE 
        SYNTAX OCTET STRING    
        ACCESS read-only 
        STATUS mandatory 
        DESCRIPTION 
            "The air flow speed in m/s, as string."
        ::= { objectEntry 245860000 }
    
    rsAirFlowSpeedInteger       OBJECT-TYPE 
        SYNTAX INTEGER         
        ACCESS read-only 
        STATUS mandatory 
        DESCRIPTION 
            "The air flow speed in m/s, as integer."
        ::= { objectEntry 245860001 }
        
    rsAirFlowSpeedIntMul100     OBJECT-TYPE 
        SYNTAX INTEGER         
        ACCESS read-only 
        STATUS mandatory 
        DESCRIPTION 
            "The air flow speed in cm/s, as integer."
        ::= { objectEntry 245860002 }

    --------------------------------------------------------------------------------------------
    -- Float value from data object 24594 (6012 hex) as string, integer and multiplied by 100 --
    --------------------------------------------------------------------------------------------

    rsSmokeLevel1String         OBJECT-TYPE 
        SYNTAX OCTET STRING    
        ACCESS read-only 
        STATUS mandatory 
        DESCRIPTION 
            "The smoke level of detector 1 in %/m obscuration, as string."
        ::= { objectEntry 245940000 }
    
    rsSmokeLevel1Integer        OBJECT-TYPE 
        SYNTAX INTEGER         
        ACCESS read-only 
        STATUS mandatory 
        DESCRIPTION 
            "The smoke level of detector 1 in %/m obscuration, as integer."
        ::= { objectEntry 245940001 }
        
    rsSmokeLevel1IntMul100      OBJECT-TYPE 
        SYNTAX INTEGER         
        ACCESS read-only 
        STATUS mandatory 
        DESCRIPTION 
            "The smoke level of detector 1 in %/cm obscuration, as integer."
        ::= { objectEntry 245940002 }

    --------------------------------------------------------------------------------------------
    -- Float value from data object 24599 (6017 hex) as string, integer and multiplied by 100 --
    --------------------------------------------------------------------------------------------

    rsSmokeLevel2String         OBJECT-TYPE 
        SYNTAX OCTET STRING    
        ACCESS read-only 
        STATUS mandatory 
        DESCRIPTION 
            "The smoke level of detector 2 in %/m obscuration, as string."
        ::= { objectEntry 245990000 }
    
    rsSmokeLevel2Integer        OBJECT-TYPE 
        SYNTAX INTEGER         
        ACCESS read-only 
        STATUS mandatory 
        DESCRIPTION 
            "The smoke level of detector 2 in %/m obscuration, as integer."
        ::= { objectEntry 245990001 }
        
    rsSmokeLevel2IntMul100      OBJECT-TYPE 
        SYNTAX INTEGER         
        ACCESS read-only 
        STATUS mandatory 
        DESCRIPTION 
            "The smoke level of detector 2 in %/cm obscuration, as integer."
        ::= { objectEntry 245990002 }

    --------------------------------------------------------------------------------------------
    -- Float value from data object 24605 (601D hex) as string, integer and multiplied by 100 --
    --------------------------------------------------------------------------------------------

    rsSensibility1String        OBJECT-TYPE 
        SYNTAX OCTET STRING    
        ACCESS read-only 
        STATUS mandatory 
        DESCRIPTION 
            "The sensitivity of detector 1 in %/m obscuration, as string."
        ::= { objectEntry 246050000 }
    
    rsSensibility1Integer       OBJECT-TYPE 
        SYNTAX INTEGER         
        ACCESS read-only 
        STATUS mandatory 
        DESCRIPTION 
            "The sensitivity of detector 1 in %/m obscuration, as integer."
        ::= { objectEntry 246050001 }
        
    rsSensibility1IntMul100     OBJECT-TYPE 
        SYNTAX INTEGER         
        ACCESS read-only 
        STATUS mandatory 
        DESCRIPTION 
            "The sensitivity of detector 1 in %/cm obscuration, as integer."
        ::= { objectEntry 246050002 }

    --------------------------------------------------------------------------------------------
    -- Float value from data object 24606 (601E hex) as string, integer and multiplied by 100 --
    --------------------------------------------------------------------------------------------

    rsSensibility2String        OBJECT-TYPE 
        SYNTAX OCTET STRING    
        ACCESS read-only 
        STATUS mandatory 
        DESCRIPTION 
            "The sensitivity of detector 2 in %/m obscuration, as string."
        ::= { objectEntry 246060000 }
    
    rsSensibility2Integer       OBJECT-TYPE 
        SYNTAX INTEGER         
        ACCESS read-only 
        STATUS mandatory 
        DESCRIPTION 
            "The sensitivity of detector 2 in %/m obscuration, as integer."
        ::= { objectEntry 246060001 }
        
    rsSensibility2IntMul100     OBJECT-TYPE 
        SYNTAX INTEGER         
        ACCESS read-only 
        STATUS mandatory 
        DESCRIPTION 
            "The sensitivity of detector 2 in %/cm obscuration, as integer."
        ::= { objectEntry 246060002 }

    --------------------------------------------------------------------------------------------
    -- Float value from data object 24607 (601F hex) as string, integer and multiplied by 100 --
    --------------------------------------------------------------------------------------------

    rsAlarmTemp1String          OBJECT-TYPE 
        SYNTAX OCTET STRING    
        ACCESS read-only 
        STATUS mandatory 
        DESCRIPTION 
            "The alarm temperature for temperature sensor 1
             in Celsius, as string."
        ::= { objectEntry 246070000 }
    
    rsAlarmTemp1Integer         OBJECT-TYPE 
        SYNTAX INTEGER         
        ACCESS read-only 
        STATUS mandatory 
        DESCRIPTION 
            "The alarm temperature for temperature sensor 1
             in Celsius, as integer."
        ::= { objectEntry 246070001 }
        
    rsAlarmTemp1IntMul100       OBJECT-TYPE 
        SYNTAX INTEGER         
        ACCESS read-only 
        STATUS mandatory 
        DESCRIPTION 
            "The alarm temperature for temperature sensor 1
             in Celsius multiplied by 100, as integer."
        ::= { objectEntry 246070002 }

    --------------------------------------------------------------------------------------------
    -- Float value from data object 24608 (6020 hex) as string, integer and multiplied by 100 --
    --------------------------------------------------------------------------------------------

    rsAlarmTemp2String          OBJECT-TYPE 
        SYNTAX OCTET STRING    
        ACCESS read-only 
        STATUS mandatory 
        DESCRIPTION 
            "The alarm temperature for temperature sensor 2
             in Celsius, as string."
        ::= { objectEntry 246080000 }
    
    rsAlarmTemp2Integer         OBJECT-TYPE 
        SYNTAX INTEGER         
        ACCESS read-only 
        STATUS mandatory 
        DESCRIPTION 
            "The alarm temperature for temperature sensor 2
             in Celsius, as integer."
        ::= { objectEntry 246080001 }
        
    rsAlarmTemp2IntMul100       OBJECT-TYPE 
        SYNTAX INTEGER         
        ACCESS read-only 
        STATUS mandatory 
        DESCRIPTION 
            "The alarm temperature for temperature sensor 2
             in Celsius multiplied by 100, as integer."
        ::= { objectEntry 246080002 }

    --------------------------------------------------------------------------------------------
    -- Float value from data object 24609 (6021 hex) as string, integer and multiplied by 100 --
    --------------------------------------------------------------------------------------------

    rsAlarmTemp3String          OBJECT-TYPE 
        SYNTAX OCTET STRING    
        ACCESS read-only 
        STATUS mandatory 
        DESCRIPTION 
            "The alarm temperature for temperature sensor 3
             in Celsius, as string."
        ::= { objectEntry 246090000 }
    
    rsAlarmTemp3Integer         OBJECT-TYPE 
        SYNTAX INTEGER         
        ACCESS read-only 
        STATUS mandatory 
        DESCRIPTION 
            "The alarm temperature for temperature sensor 3
             in Celsius, as integer."
        ::= { objectEntry 246090001 }
        
    rsAlarmTemp3IntMul100       OBJECT-TYPE 
        SYNTAX INTEGER         
        ACCESS read-only 
        STATUS mandatory 
        DESCRIPTION 
            "The alarm temperature for temperature sensor 3
             in Celsius multiplied by 100, as integer."
        ::= { objectEntry 246090002 }

    --------------------------------------------------------------------------------------------
    -- Float value from data object 24610 (6022 hex) as string, integer and multiplied by 100 --
    --------------------------------------------------------------------------------------------

    rsAlarmTemp4String          OBJECT-TYPE 
        SYNTAX OCTET STRING    
        ACCESS read-only 
        STATUS mandatory 
        DESCRIPTION 
            "The alarm temperature for temperature sensor 4
             in Celsius, as string."
        ::= { objectEntry 246100000 }
    
    rsAlarmTemp4Integer         OBJECT-TYPE 
        SYNTAX INTEGER         
        ACCESS read-only 
        STATUS mandatory 
        DESCRIPTION 
            "The alarm temperature for temperature sensor 4
             in Celsius, as integer."
        ::= { objectEntry 246100001 }
        
    rsAlarmTemp4IntMul100       OBJECT-TYPE 
        SYNTAX INTEGER         
        ACCESS read-only 
        STATUS mandatory 
        DESCRIPTION 
            "The alarm temperature for temperature sensor 4
             in Celsius multiplied by 100, as integer."
        ::= { objectEntry 246100002 }

    --------------------------------------------------------------------------------------------
    -- Float value from data object 24611 (6023 hex) as string, integer and multiplied by 100 --
    --------------------------------------------------------------------------------------------

    rsAlarmTemp5String          OBJECT-TYPE 
        SYNTAX OCTET STRING    
        ACCESS read-only 
        STATUS mandatory 
        DESCRIPTION 
            "The alarm temperature for temperature sensor 5
             in Celsius, as string."
        ::= { objectEntry 246110000 }
    
    rsAlarmTemp5Integer         OBJECT-TYPE 
        SYNTAX INTEGER         
        ACCESS read-only 
        STATUS mandatory 
        DESCRIPTION 
            "The alarm temperature for temperature sensor 5
             in Celsius, as integer."
        ::= { objectEntry 246110001 }
        
    rsAlarmTemp5IntMul100       OBJECT-TYPE 
        SYNTAX INTEGER         
        ACCESS read-only 
        STATUS mandatory 
        DESCRIPTION 
            "The alarm temperature for temperature sensor 5
             in Celsius multiplied by 100, as integer."
        ::= { objectEntry 246110002 }

    --------------------------------------------------------------------------------------------
    -- Float value from data object 24612 (6024 hex) as string, integer and multiplied by 100 --
    --------------------------------------------------------------------------------------------

    rsFanVoltageString          OBJECT-TYPE 
        SYNTAX OCTET STRING    
        ACCESS read-only 
        STATUS mandatory 
        DESCRIPTION 
            "The fan voltage in volt, as string."
        ::= { objectEntry 246120000 }
    
    rsFanVoltageInteger         OBJECT-TYPE 
        SYNTAX INTEGER         
        ACCESS read-only 
        STATUS mandatory 
        DESCRIPTION 
            "The fan voltage in volt, as integer."
        ::= { objectEntry 246120001 }
        
    rsFanVoltageIntMul100       OBJECT-TYPE 
        SYNTAX INTEGER         
        ACCESS read-only 
        STATUS mandatory 
        DESCRIPTION 
            "The fan voltage in volt, multiplied by 100, as integer."
        ::= { objectEntry 246120002 }

    --------------------------------------------------------------------------------------------
    -- Float value from data object 24626 (6032 hex) as string, integer and multiplied by 100 --
    --------------------------------------------------------------------------------------------

    rsFlowReferenceString          OBJECT-TYPE 
        SYNTAX OCTET STRING    
        ACCESS read-only 
        STATUS mandatory 
        DESCRIPTION 
            "The air flow reference value in m/s, as string."
        ::= { objectEntry 246260000 }
    
    rsFlowReferenceInteger         OBJECT-TYPE 
        SYNTAX INTEGER         
        ACCESS read-only 
        STATUS mandatory 
        DESCRIPTION 
            "The air flow reference value in m/s, as integer."
        ::= { objectEntry 246260001 }
        
    rsFlowReferenceIntMul100       OBJECT-TYPE 
        SYNTAX INTEGER         
        ACCESS read-only 
        STATUS mandatory 
        DESCRIPTION 
            "The air flow reference value in m/s, multiplied by 100, as integer."
        ::= { objectEntry 246260002 }

END
