USP-SES-TRAP-MIB DEFINITIONS ::= BEGIN

IMPORTS 
    OBJECT-TYPE, MODULE-IDENTITY, NOTIFICATION-TYPE FROM SNMPv2-SMI
    DisplayString FROM SNMPv2-TC
    OBJECT-GROUP, NOTIFICATION-GROUP FROM SNMPv2-CONF
    ses FROM USP-SES-MIB
    ;
            
uspSesTrapMib MODULE-IDENTITY
LAST-UPDATED   "201206260000Z"
ORGANIZATION   "United Security Providers AG"
CONTACT-INFO   "United Security Providers AG
                Stauffacherstrasse 65/15
                CH-3014 Bern
                http://www.united-security-providers.ch"
DESCRIPTION    "MIB module for the USP Secure Entry Server"
::= { ses 300 0 }

event          OBJECT IDENTIFIER ::= { ses 300 }
traps          OBJECT IDENTIFIER ::= { event 900 }
notif          OBJECT IDENTIFIER ::= { traps 0 }

-- event

eventId OBJECT-TYPE
		SYNTAX DisplayString
		MAX-ACCESS read-only
		STATUS current
		DESCRIPTION "event identifier"
		::= { event 1 }

eventLevel OBJECT-TYPE
    SYNTAX INTEGER { emerg(0),alert(1),crit(2),err(3),warning(4),notice(5),info(6),debug(7) }
    MAX-ACCESS read-only
    STATUS current
    DESCRIPTION "event message severity"
    ::= { event 2 }
                
eventServerName OBJECT-TYPE
		SYNTAX DisplayString
		MAX-ACCESS read-only
		STATUS current
		DESCRIPTION "Server name (virtual host) or 'base server' for core components"
		::= { event 3 }

eventComponentName OBJECT-TYPE
		SYNTAX DisplayString
		MAX-ACCESS read-only
		STATUS current
		DESCRIPTION "Component name, either htl, hts, srm, or system"
		::= { event 4 }

eventModuleName OBJECT-TYPE
		SYNTAX DisplayString
		MAX-ACCESS read-only
		STATUS current
		DESCRIPTION "Module name"
		::= { event 5 }

eventDescription OBJECT-TYPE
		SYNTAX DisplayString
		MAX-ACCESS read-only
		STATUS current
		DESCRIPTION "event message text describing the event"
		::= { event 6 }
               
trapGroup       OBJECT-GROUP
                OBJECTS { eventId, eventLevel, eventServerName, eventComponentName, eventModuleName, eventDescription }
                STATUS current
                DESCRIPTION "USP SES trap group"
                ::= { ses 1 }


eventTrap      NOTIFICATION-TYPE
               OBJECTS      { eventId, eventLevel, eventServerName, eventComponentName, eventModuleName, eventDescription }
               STATUS       current
               DESCRIPTION     "USP SES event notification"
               ::= { notif 1 }

uspSesNotifGroup NOTIFICATION-GROUP
               NOTIFICATIONS { eventTrap }
               STATUS current
               DESCRIPTION "USP SES notification group"
               ::= { traps 1 }

END
