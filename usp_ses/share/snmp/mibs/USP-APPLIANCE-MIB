USP-APPLIANCE-MIB DEFINITIONS ::= BEGIN

IMPORTS
		MODULE-IDENTITY, OBJECT-TYPE, Counter32, Gauge32, Unsigned32 FROM SNMPv2-SMI
		DisplayString, TruthValue FROM SNMPv2-TC
		OBJECT-GROUP FROM SNMPv2-CONF
		usp FROM USP-MIB
		;

appliance MODULE-IDENTITY
		LAST-UPDATED   "201702200000Z"
		ORGANIZATION   "United Security Providers"
		CONTACT-INFO   "United Security Providers AG
		                Stauffacherstrasse 65
		                CH-3014 Bern"
		DESCRIPTION    "MIB module for the USP Appliance System
		                Created by the USP MibGen tool based on the mib configuration file sab\usp_appliance_mib_config.xml version 0.1"
		REVISION       "201211280000Z"
		DESCRIPTION    "First version of the MIB generated with MibGen"
		REVISION       "201610310000Z"
		DESCRIPTION    "Added new MIB nodes for fans, power supplies and raid disc status"
		REVISION       "201702200000Z"
		DESCRIPTION    "Added new MIB node memAvailable for reporting of available system memory"
		 ::= { usp 7419 }

traps OBJECT IDENTIFIER ::= { appliance 1 }

trapObjects OBJECT IDENTIFIER ::= { traps 1 }

notificationGroups OBJECT IDENTIFIER ::= { traps 2 }

objectGroups OBJECT IDENTIFIER ::= { appliance 2 }

applianceGroup OBJECT-GROUP
		OBJECTS {
				aplDescription, aplUptime, aplContact, 
				aplHostname, aplLocation, aplRelease
		}
		STATUS current
		DESCRIPTION "applianceGroup"
		::= { objectGroups 0 }

hardwareGroup OBJECT-GROUP
		OBJECTS {
				hwInfo
		}
		STATUS current
		DESCRIPTION "hardwareGroup"
		::= { objectGroups 1 }

powersupplyGroup OBJECT-GROUP
		OBJECTS {
				psInstalled, psActive
		}
		STATUS current
		DESCRIPTION "powersupplyGroup"
		::= { objectGroups 3 }

fansGroup OBJECT-GROUP
		OBJECTS {
				fInstalled, fActive
		}
		STATUS current
		DESCRIPTION "fansGroup"
		::= { objectGroups 4 }

raiddiscsGroup OBJECT-GROUP
		OBJECTS {
				rdInstalled, rdActive
		}
		STATUS current
		DESCRIPTION "raiddiscsGroup"
		::= { objectGroups 5 }

sysloadGroup OBJECT-GROUP
		OBJECTS {
				slLong, slMid, slShort
		}
		STATUS current
		DESCRIPTION "sysloadGroup"
		::= { objectGroups 6 }

cpuGroup OBJECT-GROUP
		OBJECTS {
				cpuVendor, cpuModel, cpuCores, 
				cpuSpeed, cpuCache
		}
		STATUS current
		DESCRIPTION "cpuGroup"
		::= { objectGroups 7 }

memoryGroup OBJECT-GROUP
		OBJECTS {
				memTotal, memUsed, memFree, 
				memShared, memBuffered, memCached, memAvailable
		}
		STATUS current
		DESCRIPTION "memoryGroup"
		::= { objectGroups 8 }

discsGroup OBJECT-GROUP
		OBJECTS {
				discNumber, discName, discTotal, 
				discUsed, discFree
		}
		STATUS current
		DESCRIPTION "discsGroup"
		::= { objectGroups 9 }

swapGroup OBJECT-GROUP
		OBJECTS {
				swpTotal, swpUsed, swpFree
		}
		STATUS current
		DESCRIPTION "swapGroup"
		::= { objectGroups 10 }

interfacesGroup OBJECT-GROUP
		OBJECTS {
				interfaceNumber, ifName, ifInOctets, 
				ifInPackets, ifInErrors, ifOutOctets, 
				ifOutPackets, ifOutErrors
		}
		STATUS current
		DESCRIPTION "interfacesGroup"
		::= { objectGroups 12 }

aplDescription OBJECT-TYPE
		SYNTAX DisplayString
		MAX-ACCESS read-only
		STATUS current
		DESCRIPTION "System description"
		::= { appliance 3 }

aplUptime OBJECT-TYPE
		SYNTAX INTEGER (0..4294967295)
		MAX-ACCESS read-only
		STATUS current
		DESCRIPTION "System uptime in seconds"
		::= { appliance 4 }

aplContact OBJECT-TYPE
		SYNTAX DisplayString
		MAX-ACCESS read-only
		STATUS current
		DESCRIPTION "System contact"
		::= { appliance 5 }

aplHostname OBJECT-TYPE
		SYNTAX DisplayString
		MAX-ACCESS read-only
		STATUS current
		DESCRIPTION "System hostname"
		::= { appliance 6 }

aplLocation OBJECT-TYPE
		SYNTAX DisplayString
		MAX-ACCESS read-only
		STATUS current
		DESCRIPTION "The physical location of the system"
		::= { appliance 7 }

aplRelease OBJECT-TYPE
		SYNTAX DisplayString
		MAX-ACCESS read-only
		STATUS current
		DESCRIPTION "The full USP Appliance release information"
		::= { appliance 8 }

hardware OBJECT IDENTIFIER ::= { appliance 10 }

hwInfo OBJECT-TYPE
		SYNTAX DisplayString
		MAX-ACCESS read-only
		STATUS current
		DESCRIPTION "Hardware product information"
		::= { hardware 1 }

powersupply OBJECT IDENTIFIER ::= { hardware 2 }

psInstalled OBJECT-TYPE
		SYNTAX Gauge32
		MAX-ACCESS read-only
		STATUS current
		DESCRIPTION "The total number of installed powersupplies"
		::= { powersupply 1 }

psActive OBJECT-TYPE
		SYNTAX Gauge32
		MAX-ACCESS read-only
		STATUS current
		DESCRIPTION "The number of currently active (fully functional) powersupplies"
		::= { powersupply 2 }

psStatus OBJECT-TYPE
		SYNTAX TruthValue
		MAX-ACCESS read-only
		STATUS current
		DESCRIPTION "The status of the powersupplies (true means ok, false indicates a failure)"
		::= { powersupply 3 }

fans OBJECT IDENTIFIER ::= { hardware 3 }

fInstalled OBJECT-TYPE
		SYNTAX Gauge32
		MAX-ACCESS read-only
		STATUS current
		DESCRIPTION "The total number of installed fans"
		::= { fans 1 }

fActive OBJECT-TYPE
		SYNTAX Gauge32
		MAX-ACCESS read-only
		STATUS current
		DESCRIPTION "The number of currently active (fully functional) fans"
		::= { fans 2 }

fStatus OBJECT-TYPE
		SYNTAX TruthValue
		MAX-ACCESS read-only
		STATUS current
		DESCRIPTION "The status of the fans (true means ok, false indicates a failure)"
		::= { fans 3 }

raiddiscs OBJECT IDENTIFIER ::= { hardware 4 }

rdInstalled OBJECT-TYPE
		SYNTAX Gauge32
		MAX-ACCESS read-only
		STATUS current
		DESCRIPTION "The total number of installed raid discs"
		::= { raiddiscs 1 }

rdActive OBJECT-TYPE
		SYNTAX Gauge32
		MAX-ACCESS read-only
		STATUS current
		DESCRIPTION "The number of currently active (fully functional) raid discs"
		::= { raiddiscs 2 }

rdStatus OBJECT-TYPE
		SYNTAX TruthValue
		MAX-ACCESS read-only
		STATUS current
		DESCRIPTION "The status of the raid discs (true means ok, false indicates a failure)"
		::= { raiddiscs 3 }

operatingsystem OBJECT IDENTIFIER ::= { appliance 11 }

sysload OBJECT IDENTIFIER ::= { operatingsystem 1 }

slLong OBJECT-TYPE
		SYNTAX DisplayString
		MAX-ACCESS read-only
		STATUS current
		DESCRIPTION "The 15 minute load average"
		::= { sysload 1 }

slMid OBJECT-TYPE
		SYNTAX DisplayString
		MAX-ACCESS read-only
		STATUS current
		DESCRIPTION "The 5 minute load average"
		::= { sysload 2 }

slShort OBJECT-TYPE
		SYNTAX DisplayString
		MAX-ACCESS read-only
		STATUS current
		DESCRIPTION "The 1 minute load average"
		::= { sysload 3 }

cpu OBJECT IDENTIFIER ::= { operatingsystem 2 }

cpuVendor OBJECT-TYPE
		SYNTAX DisplayString
		MAX-ACCESS read-only
		STATUS current
		DESCRIPTION "CPU vendor"
		::= { cpu 1 }

cpuModel OBJECT-TYPE
		SYNTAX DisplayString
		MAX-ACCESS read-only
		STATUS current
		DESCRIPTION "CPU model"
		::= { cpu 2 }

cpuCores OBJECT-TYPE
		SYNTAX Gauge32
		MAX-ACCESS read-only
		STATUS current
		DESCRIPTION "Number of cores"
		::= { cpu 3 }

cpuSpeed OBJECT-TYPE
		SYNTAX INTEGER (0..65535)
		MAX-ACCESS read-only
		STATUS current
		DESCRIPTION "CPU speed in MHz"
		::= { cpu 4 }

cpuCache OBJECT-TYPE
		SYNTAX INTEGER (0..65535)
		MAX-ACCESS read-only
		STATUS current
		DESCRIPTION "CPU cache in KB"
		::= { cpu 5 }

memory OBJECT IDENTIFIER ::= { operatingsystem 3 }

memTotal OBJECT-TYPE
		SYNTAX INTEGER (0..4294967295)
		MAX-ACCESS read-only
		STATUS current
		DESCRIPTION "The total amount of memory in MB"
		::= { memory 1 }

memUsed OBJECT-TYPE
		SYNTAX INTEGER (0..4294967295)
		MAX-ACCESS read-only
		STATUS current
		DESCRIPTION "The amount of memory currently being used in MB"
		::= { memory 2 }

memFree OBJECT-TYPE
		SYNTAX INTEGER (0..4294967295)
		MAX-ACCESS read-only
		STATUS current
		DESCRIPTION "The total amount of memory free or available for use in MB"
		::= { memory 3 }

memShared OBJECT-TYPE
		SYNTAX INTEGER (0..4294967295)
		MAX-ACCESS read-only
		STATUS current
		DESCRIPTION "The total amount of shared memory in MB"
		::= { memory 4 }

memBuffered OBJECT-TYPE
		SYNTAX INTEGER (0..4294967295)
		MAX-ACCESS read-only
		STATUS current
		DESCRIPTION "The amount of memory currently allocated as buffered memory in MB"
		::= { memory 5 }

memCached OBJECT-TYPE
		SYNTAX INTEGER (0..4294967295)
		MAX-ACCESS read-only
		STATUS current
		DESCRIPTION "The amount of memory currently allocated as cached memory in MB"
		::= { memory 6 }

memAvailable OBJECT-TYPE
		SYNTAX INTEGER (0..4294967295)
		MAX-ACCESS read-only
		STATUS current
		DESCRIPTION "The amount of currently available memory in MB"
		::= { memory 7 }

discs OBJECT IDENTIFIER ::= { operatingsystem 4 }

discNumber OBJECT-TYPE
		SYNTAX Gauge32
		MAX-ACCESS read-only
		STATUS current
		DESCRIPTION "The amount of logical disc parts as defined for the system"
		::= { discs 1 }

discTable OBJECT-TYPE
		SYNTAX SEQUENCE OF DiscEntry
		MAX-ACCESS not-accessible
		STATUS current
		DESCRIPTION "Disc information"
		::= { discs 2 }

discEntry OBJECT-TYPE
		SYNTAX DiscEntry
		MAX-ACCESS not-accessible
		STATUS current
		DESCRIPTION "discEntry"
		INDEX { discIndex }
		::= { discTable 1 }

DiscEntry ::= SEQUENCE {
		discIndex Unsigned32,
		discName DisplayString,
		discTotal INTEGER (0..4294967295),
		discUsed INTEGER (0..4294967295),
		discFree INTEGER (0..4294967295)
}

discIndex OBJECT-TYPE
		SYNTAX Unsigned32
		MAX-ACCESS not-accessible
		STATUS current
		DESCRIPTION "A unique value for each logical disc part.  Its value
					ranges between 1 and the total discEntries."
		::= { discEntry 1 }

discName OBJECT-TYPE
		SYNTAX DisplayString
		MAX-ACCESS read-only
		STATUS current
		DESCRIPTION "The name for the logical discs part (e.g. read-only or read-write disc)"
		::= { discEntry 2 }

discTotal OBJECT-TYPE
		SYNTAX INTEGER (0..4294967295)
		MAX-ACCESS read-only
		STATUS current
		DESCRIPTION "Total space on the disc in MB"
		::= { discEntry 3 }

discUsed OBJECT-TYPE
		SYNTAX INTEGER (0..4294967295)
		MAX-ACCESS read-only
		STATUS current
		DESCRIPTION "Used space on the disc in MB"
		::= { discEntry 4 }

discFree OBJECT-TYPE
		SYNTAX INTEGER (0..4294967295)
		MAX-ACCESS read-only
		STATUS current
		DESCRIPTION "Free space on the disc in MB"
		::= { discEntry 5 }

swap OBJECT IDENTIFIER ::= { operatingsystem 5 }

swpTotal OBJECT-TYPE
		SYNTAX INTEGER (0..4294967295)
		MAX-ACCESS read-only
		STATUS current
		DESCRIPTION "Total swap space in MB"
		::= { swap 1 }

swpUsed OBJECT-TYPE
		SYNTAX INTEGER (0..4294967295)
		MAX-ACCESS read-only
		STATUS current
		DESCRIPTION "Used swap space in MB"
		::= { swap 2 }

swpFree OBJECT-TYPE
		SYNTAX INTEGER (0..4294967295)
		MAX-ACCESS read-only
		STATUS current
		DESCRIPTION "Free swap space in MB"
		::= { swap 3 }

network OBJECT IDENTIFIER ::= { operatingsystem 6 }

interfaces OBJECT IDENTIFIER ::= { network 1 }

interfaceNumber OBJECT-TYPE
		SYNTAX Gauge32
		MAX-ACCESS read-only
		STATUS current
		DESCRIPTION "The number of external network interfaces (regardless 
				of their current state) present on this system."
		::= { interfaces 1 }

interfaceTable OBJECT-TYPE
		SYNTAX SEQUENCE OF InterfaceEntry
		MAX-ACCESS not-accessible
		STATUS current
		DESCRIPTION "A list of interface entries.  The number of 
				entries is given by the value of number."
		::= { interfaces 2 }

interfaceEntry OBJECT-TYPE
		SYNTAX InterfaceEntry
		MAX-ACCESS not-accessible
		STATUS current
		DESCRIPTION "interfaceEntry"
		INDEX { ifIndex }
		::= { interfaceTable 1 }

InterfaceEntry ::= SEQUENCE {
		ifIndex Unsigned32,
		ifName DisplayString,
		ifInOctets Counter32,
		ifInPackets Counter32,
		ifInErrors Counter32,
		ifOutOctets Counter32,
		ifOutPackets Counter32,
		ifOutErrors Counter32
}

ifIndex OBJECT-TYPE
		SYNTAX Unsigned32
		MAX-ACCESS not-accessible
		STATUS current
		DESCRIPTION "A unique value for each interface.  Its value 
				ranges between 1 and the value of interfaceNumber."
		::= { interfaceEntry 1 }

ifName OBJECT-TYPE
		SYNTAX DisplayString
		MAX-ACCESS read-only
		STATUS current
		DESCRIPTION "A textual string containing the name of the interface."
		::= { interfaceEntry 2 }

ifInOctets OBJECT-TYPE
		SYNTAX Counter32
		MAX-ACCESS read-only
		STATUS current
		DESCRIPTION "The total number of octets received on the interface"
		::= { interfaceEntry 3 }

ifInPackets OBJECT-TYPE
		SYNTAX Counter32
		MAX-ACCESS read-only
		STATUS current
		DESCRIPTION "The total number of packets received on the interface"
		::= { interfaceEntry 4 }

ifInErrors OBJECT-TYPE
		SYNTAX Counter32
		MAX-ACCESS read-only
		STATUS current
		DESCRIPTION "The number of inbound packets that contained 
		        errors preventing them from being deliverable to a 
				higher-layer protocol."
		::= { interfaceEntry 5 }

ifOutOctets OBJECT-TYPE
		SYNTAX Counter32
		MAX-ACCESS read-only
		STATUS current
		DESCRIPTION "The total number of octets sent on the interface"
		::= { interfaceEntry 6 }

ifOutPackets OBJECT-TYPE
		SYNTAX Counter32
		MAX-ACCESS read-only
		STATUS current
		DESCRIPTION "The total number of packets sent on the interface"
		::= { interfaceEntry 7 }

ifOutErrors OBJECT-TYPE
		SYNTAX Counter32
		MAX-ACCESS read-only
		STATUS current
		DESCRIPTION "The number of outbound packets that contained 
		        errors preventing them from being deliverable to a 
				higher-layer protocol."
		::= { interfaceEntry 8 }

END
