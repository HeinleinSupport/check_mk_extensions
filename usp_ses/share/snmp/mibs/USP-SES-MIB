USP-SES-MIB DEFINITIONS ::= BEGIN

IMPORTS
		MODULE-IDENTITY, OBJECT-TYPE, Gauge32, Unsigned32 FROM SNMPv2-SMI
		DisplayString, TruthValue FROM SNMPv2-TC
		OBJECT-GROUP FROM SNMPv2-CONF
		usp FROM USP-MIB
		;

ses MODULE-IDENTITY
		LAST-UPDATED   "201310110000Z"
		ORGANIZATION   "United Security Providers"
		CONTACT-INFO   "United Security Providers
		                Stauffacherstrasse 65
		                CH-3014 Bern"
		DESCRIPTION    "MIB module for the USP Secure Entry Server
		                Created by the USP MibGen tool based on the mib configuration file ses/usp_ses_mib_config.xml version 0.1"
		REVISION       "201310100000Z"
		DESCRIPTION    "Extended status information"
		REVISION       "201211280000Z"
		DESCRIPTION    "First version of the MIB generated with MibGen"
		 ::= { usp 5911 }

traps OBJECT IDENTIFIER ::= { ses 1 }

trapObjects OBJECT IDENTIFIER ::= { traps 1 }

notificationGroups OBJECT IDENTIFIER ::= { traps 2 }

objectGroups OBJECT IDENTIFIER ::= { ses 2 }

hspGroup OBJECT-GROUP
		OBJECTS {
				hspCdsUsage, hspHtlRunning, hspHtsRunning, 
				hspSrmRunning
		}
		STATUS current
		DESCRIPTION "hspGroup"
		::= { objectGroups 3 }

slsGroup OBJECT-GROUP
		OBJECTS {
				slsRunning
		}
		STATUS current
		DESCRIPTION "slsGroup"
		::= { objectGroups 4 }

fuseGroup OBJECT-GROUP
		OBJECTS {
				fuseRunning
		}
		STATUS current
		DESCRIPTION "fuseGroup"
		::= { objectGroups 5 }

guiGroup OBJECT-GROUP
		OBJECTS {
				guiRunning, guiRcsStatus, guiFoMode, 
				guiFoStatus
		}
		STATUS current
		DESCRIPTION "guiGroup"
		::= { objectGroups 6 }

vhostsGroup OBJECT-GROUP
		OBJECTS {
				vhostNumber, vhostName, vhostClientConnections, 
				vhostRequestPerSecond, vhostActiveUsers, vhostAvgRequestTime
		}
		STATUS current
		DESCRIPTION "vhostsGroup"
		::= { objectGroups 7 }

eventsGroup OBJECT-GROUP
		OBJECTS {
				eventNumber, eventId, eventLevel, 
				eventServerName, eventComponentName, eventModuleName, 
				eventDescription
		}
		STATUS current
		DESCRIPTION "eventsGroup"
		::= { objectGroups 8 }

status OBJECT IDENTIFIER ::= { ses 100 }

components OBJECT IDENTIFIER ::= { status 1 }

hsp OBJECT IDENTIFIER ::= { components 1 }

hspCdsUsage OBJECT-TYPE
		SYNTAX Gauge32
		MAX-ACCESS read-only
		STATUS current
		DESCRIPTION "Usage of the client data store memory"
		::= { hsp 1 }

hspHtlRunning OBJECT-TYPE
		SYNTAX TruthValue
		MAX-ACCESS read-only
		STATUS current
		DESCRIPTION "True if the HTL component of the HSP is running"
		::= { hsp 2 }

hspHtsRunning OBJECT-TYPE
		SYNTAX TruthValue
		MAX-ACCESS read-only
		STATUS current
		DESCRIPTION "True if the HTS component of the HSP is running"
		::= { hsp 3 }

hspSrmRunning OBJECT-TYPE
		SYNTAX TruthValue
		MAX-ACCESS read-only
		STATUS current
		DESCRIPTION "True if the SRM component of the HSP is running"
		::= { hsp 4 }

sls OBJECT IDENTIFIER ::= { components 2 }

slsRunning OBJECT-TYPE
		SYNTAX TruthValue
		MAX-ACCESS read-only
		STATUS current
		DESCRIPTION "True if the SLS is running"
		::= { sls 1 }

fuse OBJECT IDENTIFIER ::= { components 3 }

fuseRunning OBJECT-TYPE
		SYNTAX TruthValue
		MAX-ACCESS read-only
		STATUS current
		DESCRIPTION "True if the FUSE is running"
		::= { fuse 1 }

gui OBJECT IDENTIFIER ::= { components 4 }

guiRunning OBJECT-TYPE
		SYNTAX TruthValue
		MAX-ACCESS read-only
		STATUS current
		DESCRIPTION "True if the SES GUI is running"
		::= { gui 1 }

guiRcsStatus OBJECT-TYPE
		SYNTAX INTEGER { clean(1),commitRequired(2),activationRequired(3),syncRequired(4) }
		MAX-ACCESS read-only
		STATUS current
		DESCRIPTION "Status of the revision controlled configuration workspace"
		::= { gui 2 }

guiFoMode OBJECT-TYPE
		SYNTAX INTEGER { disabled(1),activeActive(2),activePassive(3) }
		MAX-ACCESS read-only
		STATUS current
		DESCRIPTION "Failover mode"
		::= { gui 3 }

guiFoStatus OBJECT-TYPE
		SYNTAX INTEGER { unknown(1),active(2),standby(3),offline(4) }
		MAX-ACCESS read-only
		STATUS current
		DESCRIPTION "Failover status"
		::= { gui 4 }

vhosts OBJECT IDENTIFIER ::= { status 2 }

vhostNumber OBJECT-TYPE
		SYNTAX Gauge32
		MAX-ACCESS read-only
		STATUS current
		DESCRIPTION "The number of configured virtual hosts"
		::= { vhosts 1 }

vhostTable OBJECT-TYPE
		SYNTAX SEQUENCE OF VhostEntry
		MAX-ACCESS not-accessible
		STATUS current
		DESCRIPTION "Virtual host information"
		::= { vhosts 2 }

vhostEntry OBJECT-TYPE
		SYNTAX VhostEntry
		MAX-ACCESS not-accessible
		STATUS current
		DESCRIPTION "vhostEntry"
		INDEX { vhostIndex }
		::= { vhostTable 1 }

VhostEntry ::= SEQUENCE {
		vhostIndex Unsigned32,
		vhostName DisplayString,
		vhostClientConnections Gauge32,
		vhostRequestPerSecond Gauge32,
		vhostActiveUsers Gauge32,
		vhostAvgRequestTime Gauge32
}

vhostIndex OBJECT-TYPE
		SYNTAX Unsigned32
		MAX-ACCESS not-accessible
		STATUS current
		DESCRIPTION "A unique value for each vhost. Its value
					ranges between 1 and the total vhostEntries."
		::= { vhostEntry 1 }

vhostName OBJECT-TYPE
		SYNTAX DisplayString
		MAX-ACCESS read-only
		STATUS current
		DESCRIPTION "Name of the virtual host"
		::= { vhostEntry 2 }

vhostClientConnections OBJECT-TYPE
		SYNTAX Gauge32
		MAX-ACCESS read-only
		STATUS current
		DESCRIPTION "Number of concurrent TCP connections"
		::= { vhostEntry 3 }

vhostRequestPerSecond OBJECT-TYPE
		SYNTAX Gauge32
		MAX-ACCESS read-only
		STATUS current
		DESCRIPTION "Requests per second"
		::= { vhostEntry 4 }

vhostActiveUsers OBJECT-TYPE
		SYNTAX Gauge32
		MAX-ACCESS read-only
		STATUS current
		DESCRIPTION "Active users"
		::= { vhostEntry 5 }

vhostAvgRequestTime OBJECT-TYPE
		SYNTAX Gauge32
		MAX-ACCESS read-only
		STATUS current
		DESCRIPTION "Average request time"
		::= { vhostEntry 6 }

events OBJECT IDENTIFIER ::= { ses 200 }

eventNumber OBJECT-TYPE
		SYNTAX Gauge32
		MAX-ACCESS read-only
		STATUS current
		DESCRIPTION "The number of current events"
		::= { events 1 }

eventTable OBJECT-TYPE
		SYNTAX SEQUENCE OF EventEntry
		MAX-ACCESS not-accessible
		STATUS current
		DESCRIPTION "Event host information"
		::= { events 2 }

eventEntry OBJECT-TYPE
		SYNTAX EventEntry
		MAX-ACCESS not-accessible
		STATUS current
		DESCRIPTION "eventEntry"
		INDEX { eventIndex }
		::= { eventTable 1 }

EventEntry ::= SEQUENCE {
		eventIndex Unsigned32,
		eventId DisplayString,
		eventLevel INTEGER { emerg(0),alert(1),crit(2),err(3),warning(4),notice(5),info(6),debug(7) },
		eventServerName DisplayString,
		eventComponentName DisplayString,
		eventModuleName DisplayString,
		eventDescription DisplayString
}

eventIndex OBJECT-TYPE
		SYNTAX Unsigned32
		MAX-ACCESS not-accessible
		STATUS current
		DESCRIPTION "A unique value for each event. Its value
					ranges between 1 and the total eventEntries."
		::= { eventEntry 1 }

eventId OBJECT-TYPE
		SYNTAX DisplayString
		MAX-ACCESS read-only
		STATUS current
		DESCRIPTION "event identifier"
		::= { eventEntry 2 }

eventLevel OBJECT-TYPE
		SYNTAX INTEGER { emerg(0),alert(1),crit(2),err(3),warning(4),notice(5),info(6),debug(7) }
		MAX-ACCESS read-only
		STATUS current
		DESCRIPTION "event message severity"
		::= { eventEntry 3 }

eventServerName OBJECT-TYPE
		SYNTAX DisplayString
		MAX-ACCESS read-only
		STATUS current
		DESCRIPTION "Server name (virtual host) or 'base server' for core components"
		::= { eventEntry 4 }

eventComponentName OBJECT-TYPE
		SYNTAX DisplayString
		MAX-ACCESS read-only
		STATUS current
		DESCRIPTION "Component name, either htl, hts, srm, or system"
		::= { eventEntry 5 }

eventModuleName OBJECT-TYPE
		SYNTAX DisplayString
		MAX-ACCESS read-only
		STATUS current
		DESCRIPTION "Module name"
		::= { eventEntry 6 }

eventDescription OBJECT-TYPE
		SYNTAX DisplayString
		MAX-ACCESS read-only
		STATUS current
		DESCRIPTION "event message text describing the event"
		::= { eventEntry 7 }

END
